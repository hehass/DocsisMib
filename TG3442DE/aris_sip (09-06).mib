ARRIS-SIP-MIB DEFINITIONS ::= BEGIN

IMPORTS
 MODULE-IDENTITY, OBJECT-TYPE, Unsigned32, Integer32, IpAddress
  FROM SNMPv2-SMI
 arris
  FROM ARRIS-MIB
 OBJECT-GROUP
  FROM SNMPv2-CONF
 TruthValue, DisplayString, TEXTUAL-CONVENTION
  FROM SNMPv2-TC
 SnmpAdminString
  FROM SNMP-FRAMEWORK-MIB
 InetAddress, InetAddressType
  FROM INET-ADDRESS-MIB;

arrisSipMib MODULE-IDENTITY
    LAST-UPDATED    "201606270000Z" -- Jun 27, 2016
    ORGANIZATION    "Arris Interactive"
    CONTACT-INFO
  "Donnie Tew
   Postal: Arris Interactive
    3871 Lakefield Drive
    Suite 300
    Suwanee, GA 30024-1242
    U.S.A.
   Phone:  +1 770 622 8500
   E-mail: donnie.tew@arrisi.com"
    DESCRIPTION
      "This is the portion of the Arris enterprise MIB that applies
       to SIP signaling."
-- Revision history
    REVISION    "201606270000Z" -- Jun 27, 2016
    DESCRIPTION
         "Add the new mib sipCfgUnsolicitedNotifyAcceptSwitch."
    REVISION    "201012300000Z" -- Dec 30, 2010
    DESCRIPTION
         "This is the portion of the Arris enterprise MIB that applies
       to SIP signaling."
    ::= { arris 11 }

sipConfiguration OBJECT IDENTIFIER ::= { arrisSipMib 1 }
sipStatus OBJECT IDENTIFIER ::= { arrisSipMib 2 }


--=====================================================================
-- SIP per port configuration data
--=====================================================================
sipCfgPortTable OBJECT-TYPE
 SYNTAX SEQUENCE OF SipCfgPortEntry
 MAX-ACCESS not-accessible
 STATUS current
 DESCRIPTION
  "This table is used to define the SIP configurable data on a per port basis."
 ::= { sipConfiguration 1 }

sipCfgPortEntry OBJECT-TYPE
 SYNTAX SipCfgPortEntry
 MAX-ACCESS not-accessible
 STATUS current
 DESCRIPTION
  "An entry in the Configuration Port table."
 INDEX { sipCfgPortPortNumber }
 ::= { sipCfgPortTable 1 }

SipCfgPortEntry ::= SEQUENCE{
  sipCfgPortPortNumber Integer32,
  sipCfgPortUserName OCTET STRING,
  sipCfgPortDisplayName DisplayString,
  sipCfgPortLogin OCTET STRING,
  sipCfgPortPassword OCTET STRING,
  sipCfgPortWarmOrHotlineNumber DisplayString,
  sipCfgPortWarmLineTimeout INTEGER,
  sipCfgPortRegistrarAdr DisplayString,
  sipCfgPortRegistrarPort Integer32,
  sipCfgPortRegistrarType INTEGER,
  sipCfgPortProxyAdr DisplayString,
  sipCfgPortProxyPort Integer32,
  sipCfgPortProxyType INTEGER,
  sipCfgPortFeatureSettings BITS,
  sipCfgPortT38Mode INTEGER,
  sipCfgPortMaxT38HSRedLevel Integer32,
  sipCfgPortFaxOnlyTimeout Integer32,
  sipCfgPortCallByeDelay Unsigned32,
  sipCfgPortMWIClear TruthValue,
  sipCfgPortMWIVisualEnable TruthValue,
  sipCfgPortMWIToneEnable TruthValue,
  sipCfgPortWarmOrHotlineEnable TruthValue,
  sipCfgPortDndRingReminderEnable TruthValue,
  sipCfgPortLoopReversal TruthValue,
  sipCfgPortCurrentProxy DisplayString,
  sipCfgPortPrimaryProxy DisplayString,
  sipCfgPortCallWaitingPermanentDisable INTEGER,
  sipCfgPortCallerIDCallWaitingPermanentDisable INTEGER
 }

sipCfgPortPortNumber OBJECT-TYPE
 SYNTAX Integer32
 MAX-ACCESS not-accessible
 STATUS current
 DESCRIPTION
  "The unique value which identifies the port."
 ::= { sipCfgPortEntry 1 }

sipCfgPortUserName OBJECT-TYPE
 SYNTAX OCTET STRING(SIZE(0..1023))
 MAX-ACCESS read-write
 STATUS current
 DESCRIPTION
  "String used for the user portion of the SIP URI for this port.  It is
   suggested that this string be the phone number of the line so that it
   can be used for Caller ID.  This object is only settable during
   config file download.  This item is the only mandatory item in this
   table for the line to be able to provide service."
 ::= { sipCfgPortEntry 2 }

sipCfgPortDisplayName OBJECT-TYPE
 SYNTAX DisplayString
 MAX-ACCESS read-write
 STATUS current
 DESCRIPTION
  "String used for the Display Name of the SIP URI. It is recommended that
   this be the name of the subscriber so that it can be used for Caller
   Name Delivery.  This object is only settable during config file download."
 ::= { sipCfgPortEntry 3 }

sipCfgPortLogin OBJECT-TYPE
 SYNTAX OCTET STRING(SIZE(0..1023))
 MAX-ACCESS read-write
 STATUS current
 DESCRIPTION
  "String used for the login name of the SIP agent for this line. This
   object is only settable during config file download.  Since this
   setting is used as part of the authentication process when read
   will only show as XXXXXXX"
 ::= { sipCfgPortEntry 4 }

sipCfgPortPassword OBJECT-TYPE
 SYNTAX OCTET STRING(SIZE(0..8192))
 MAX-ACCESS read-write
 STATUS current
 DESCRIPTION
  "String used for the password of the SIP agent for this line. This
   object is only settable during config file download.  Since this
   setting is used as part of the authentication process when read
   will only show as XXXXXXX"
 ::= { sipCfgPortEntry 5 }

sipCfgPortWarmOrHotlineNumber OBJECT-TYPE
 SYNTAX DisplayString
 MAX-ACCESS read-write
 STATUS current
 DESCRIPTION
  "To enable the warm or hotline feature on the line, this object must be set
   to the phone number that will be called for the feature.  For the warmline
   feature this number should be set as well as the timeout object
   sipCfgPortWarmLineTimeout for the timer before we send out the INVITE to
   the line.  For the hotline feature, this MIB should be set and the
   sipCfgPortWarmLineTimeout object should be set to 0 (its default value)."
 ::= { sipCfgPortEntry 6 }

sipCfgPortWarmLineTimeout OBJECT-TYPE
 SYNTAX INTEGER
 MAX-ACCESS read-write
 STATUS current
 DESCRIPTION
  "This setting is used as the timer (in seconds) for the period of time
   after an offhook before an INVITE for the warmline number is sent.
   The default value for this object is 5 seconds."
 DEFVAL { 5 }
 ::= { sipCfgPortEntry 7 }

sipCfgPortRegistrarAdr OBJECT-TYPE
 SYNTAX DisplayString
 MAX-ACCESS read-write
 STATUS current
 DESCRIPTION
  "This is the address of the SIP registrar server for this line.  This object is only
   settable during config file download. It this object is used it will take precedence
   over any setting to the sipCfgRegistrarAdr MIB object for this line."
 ::= { sipCfgPortEntry 8 }

sipCfgPortRegistrarPort OBJECT-TYPE
 SYNTAX Integer32
 MAX-ACCESS read-write
 STATUS current
 DESCRIPTION
  "This is the port of the SIP registrar server for this line.  This object is only
   settable during config file download. It this object is used it will take precedence
   over any setting to the sipCfgRegistrarAdr MIB object for this line."
 ::= { sipCfgPortEntry 9 }

sipCfgPortRegistrarType OBJECT-TYPE
 SYNTAX INTEGER{
                ipv4(0),
                dns(1)}
 MAX-ACCESS read-write
 STATUS current
 DESCRIPTION
  "This is the type for the address of the SIP registrar server for this line. This object
   is only settable during config file download. It this object is used it will take
   precedence over any setting to the sipCfgRegistrarAdr MIB object for this line."
 ::= { sipCfgPortEntry 10 }

sipCfgPortProxyAdr OBJECT-TYPE
 SYNTAX DisplayString
 MAX-ACCESS read-write
 STATUS current
 DESCRIPTION
  "This is the address of the SIP proxy server for this line.  This can be the same server
   as the registrar server. This object is only settable during config file download. It this
   object is used it will take precedence over any setting to the sipCfgProxyAdr MIB object
   for this line."
 ::= { sipCfgPortEntry 11 }

sipCfgPortProxyPort OBJECT-TYPE
 SYNTAX Integer32
 MAX-ACCESS read-write
 STATUS current
 DESCRIPTION
  "This is the port of the SIP proxy server for this line.  This object is only settable
   during config file download. It this object is used it will take precedence over any
   setting to the sipCfgProxyAdr MIB object for this line."
 ::= { sipCfgPortEntry 12 }

sipCfgPortProxyType OBJECT-TYPE
 SYNTAX INTEGER{
                ipv4(0),
                dns(1)}
 MAX-ACCESS read-write
 STATUS current
 DESCRIPTION
  "This is the type for the address of the SIP proxy server for this line. This object
   is only settable during config file download. It this object is used it will take
   precedence over any setting to the sipCfgProxyAdr MIB object for this line."
 ::= { sipCfgPortEntry 13 }

sipCfgPortFeatureSettings OBJECT-TYPE
    SYNTAX BITS {
        defaultFeatures(0),
        callerIdPermanentDisable(1),
        anonCallRejectionEnable(2),
        callWaitingPermanentDisable(3),
        threeWayCallingDisable(4),
        callerIdReceiptDisable(5),
        callTransferEnable(6)
    }
 MAX-ACCESS read-write
 STATUS current
 DESCRIPTION
  "This object allows for MSO control of certain feature states via the config file.
   If the settings for these features do not need to be set a certain way at
   powerup, then this MIB should not be used.  This MIB is not settable via SNMP.

   When read this object will show the current state of the features on the line.

   /** BIT Descriptions **/
   0x40 - Setting of the callerIdPermanentDisable(1) bit means that the default
   outbound caller ID method is caller ID restrictive. Default is for caller ID
   info to be presented to the callee.

   0x20 - Setting of the anonCallRejectionEnable(2) bit means that the anonymous
   call rejection feature will be enabled until disabled via star code by the user
   or by removal of the setting via SNMP update.

   0x10 - Setting of the callWaitingPermanentDisable(3) bit means that call waiting
   will be deactivated for this line.

   0x08 - Setting of the threeWayCallingDisable(4) bit will disable the hook flash
   processing while the user is in an active call.  This will disable the user from
   placing a three way call.

   0x04 - Setting of the callerIdReceiptDisable(5) bit will disable local caller ID
   display.

   0x02 - Setting of the callTransferEnable(6) bit will enable the call transfer
   feature."
 ::= { sipCfgPortEntry 14 }

sipCfgPortT38Mode OBJECT-TYPE
 SYNTAX INTEGER{
                t38Off(1),
                t38Loose(2),
                t38Strict(3)}

 MAX-ACCESS read-write
 STATUS current
 DESCRIPTION
  "This object is used to enable T38 mode for the line.  By default T38 is disabled. To
   enable it this value must be set to t38Loose or t38Strict.  In t38Loose mode T38
   negotiation will be attempted without prior knowledge of the other ends support
   for T38.  In t38Strict mode, the endpoint will not attempt a T38 transition
   unless the other end has advertised capabilites for T38 support."
 DEFVAL { t38Off }
 ::= { sipCfgPortEntry 15 }

sipCfgPortFaxOnlyTimeout OBJECT-TYPE
 SYNTAX Integer32 (0..600)
 MAX-ACCESS read-write
 STATUS current
 DESCRIPTION
  "This object is used to define a line as a fax only line.  The default value of the
   object is zero which means no timeout.  When the object is set to a non-zero value
   a timer is started after receiving the far ends SDP.  If this timer pops without
   having received fax/modem tones on the connection the call will be dropped.  Its
   units are in seconds."
 DEFVAL { 0 }
 ::= { sipCfgPortEntry 16 }

sipCfgPortMaxT38HSRedLevel OBJECT-TYPE
 SYNTAX Integer32(0..2)
 MAX-ACCESS read-write
 STATUS current
 DESCRIPTION
  "This MIB is used to set the maximum high-speed redundancy level that will be used for
   T.38 fax-relay in both the send and receive direction.  High speed redundancy refers
   to the number of additional older data packets included in each T.38 datagram when
   transferring fax data between endpoints.  For example, if an endpoint is transmitting
   T.38 with a high-speed redundancy level of two and the current sequence number of the
   data packet is 15, two older (i.e. previously transmitted) data packets with sequence
   numbers 13 and 14 are included in the T.38 datagram.  In general, this makes T.38
   data transmission much less susceptible to packet loss in the network.  This parameter
   is configuration to restrict the amount of bandwidth used for T.38 transmission.

   Setting the maximum high-speed redundancy level does not necessarily mean that the
   endpoint will always transmit and receive at that level.  The endpoint will attempt to
   transmit at that level only if allowed by the remote endpoint.  During call setup the
   remote endpoint may provide the T38FaxMaxDatagram attribute within its SDP indicating
   the maximum datagram size that it is able to receive.  If this number is smaller than
   is needed to transmit at the maximum level, the redundancy will be reduced accordingly.

   Likewise, the local endpoint will construct its T38FaxMaxDatagram attribute according
   to the maximum high-speed redundancy level configured to restrict the far end from
   sending T.38 datagram packets with a higher level of high-speed redundancy.  This does
   not necessarily mean that the remote endpoint will transmit at the maximum high-speed
   redundancy configured, but does guarantee that it will not transmit at a higher level.
   The remote endpoint may be configured to transmit at a lower high-speed redundancy level,
   or may choose to reduce the transmission speed to reduce the bandwidth consumption."
 DEFVAL { 1 }
 ::= { sipCfgPortEntry 17 }

sipCfgPortCallByeDelay OBJECT-TYPE
 SYNTAX Unsigned32
 MAX-ACCESS read-write
 STATUS current
 DESCRIPTION
  "This MIB Object specifies the Bye Delay in seconds per line."
 DEFVAL { 0 }
 ::= { sipCfgPortEntry 18 }

sipCfgPortMWIClear OBJECT-TYPE
 SYNTAX TruthValue
 MAX-ACCESS read-write
 STATUS current
 DESCRIPTION
  "This MIB is used to clear or set the current MWI. If the MIB is set to FALSE, then the MTA will turn on both MWI tone
   and visual MWI indicator. If the MIB is set to TRUE, the tone and indicator will be cleared. The Get operation of this MIB Object
   will always return FALSE."
 DEFVAL { false }
 ::= { sipCfgPortEntry 19 }

sipCfgPortMWIVisualEnable OBJECT-TYPE
 SYNTAX TruthValue
 MAX-ACCESS read-write
 STATUS current
 DESCRIPTION
  "This MIB Object enables or disables the visual indication for the MWI NOTIFY."
 DEFVAL { true }
 ::= { sipCfgPortEntry 20 }

sipCfgPortMWIToneEnable OBJECT-TYPE
 SYNTAX TruthValue
 MAX-ACCESS read-write
 STATUS current
 DESCRIPTION
  "This MIB Object enables or disables the stutter tone indication for the MWI NOTIFY."
 DEFVAL { true }
 ::= { sipCfgPortEntry 21 }

sipCfgPortWarmOrHotlineEnable OBJECT-TYPE
 SYNTAX TruthValue
 MAX-ACCESS read-write
 STATUS current
 DESCRIPTION
  "This MIB Object enables or disables the Warmline or Hotline feature.
   sipCfgPortWarmOrHotlineNumber needs to be set to fully enable this feature."
 DEFVAL { true }
 ::= { sipCfgPortEntry 22 }

 sipCfgPortDndRingReminderEnable OBJECT-TYPE
 SYNTAX TruthValue
 MAX-ACCESS read-write
 STATUS current
 DESCRIPTION
  "This MIB Object enables or disables the ringsplash when an IVNITE is rejected by DND."
 DEFVAL { false }
 ::= { sipCfgPortEntry 23 }

sipCfgPortLoopReversal OBJECT-TYPE
 SYNTAX TruthValue
 MAX-ACCESS read-write
 STATUS current
 DESCRIPTION
  "This MIB Object enables or disables the loop polarity/reversal.When enabled(1),it indicates
  that if the line is calling party, it will reverse the polarity when the far end answers, then
  set back to normal when the call is completed. If the line is called party, it will reverse the
  polarity when ringing or talking and remain reversed if called party hangs up first."
 DEFVAL { false }
 ::= { sipCfgPortEntry 24 }

 sipCfgPortCurrentProxy OBJECT-TYPE
 SYNTAX DisplayString
 MAX-ACCESS read-only
 STATUS current
 DESCRIPTION
  "This is the address of the SIP proxy currently used by the line."
 ::= { sipCfgPortEntry 25 }

 sipCfgPortPrimaryProxy OBJECT-TYPE
 SYNTAX DisplayString
 MAX-ACCESS read-only
 STATUS current
 DESCRIPTION
  "This is the primary proxy of the line. Only used in PC2.0 load."
 ::= { sipCfgPortEntry 26 }

 sipCfgPortCallWaitingPermanentDisable OBJECT-TYPE
 SYNTAX INTEGER {
 	ignore(0),
 	forceDisable(1),
 	forceEnable(2)
	 }
 MAX-ACCESS read-write
 STATUS current
 DESCRIPTION
  "This Mib is used for setting the persistent state of Call waiting.There are three value for setting: ignore, forceDisable, forceEnable.
  If this MIB is set to ignore(0),call waiting state will be based on the setting of pktcEUERSTAppAdminStat and the persistent value will be set to default.
  If this MIB is set to forceDisable(1),MTA will ignore the configuration file, and pktcEUERSTAppAdminStat will be set to inactive state when MTA boot up.
  pktcEUERSTAppAdminStat will be changed via snmpset also, but the persistent state will not be changed.
  If this MIB is set to forceEnable(2),MTA will ignore the configuration file, and pktcEUERSTAppAdminStat will be set to active state when MTA boot up.
  pktcEUERSTAppAdminStat will be changed via snmpset also, but the persistent state will not be changed."
 ::= { sipCfgPortEntry 27 }

 sipCfgPortCallerIDCallWaitingPermanentDisable  OBJECT-TYPE
 SYNTAX INTEGER {
 	ignore(0),
 	forceDisable(1),
 	forceEnable(2)
	 }
 MAX-ACCESS read-write
 STATUS current
 DESCRIPTION
 "This Mib is used for setting the persistent state of caller ID display in a call waiting scenario.
  There are three value for setting: ignore, forceDisable, forceEnable.
  If this MIB is set to ignore(0), the Caller ID display during Call Waiting status will be based on the setting of
   MIB pktcEUERSTCIDDisCIDCWActStat and disableCwCid(6)in sipCfgSipFeatureSwitch and the persistent value will be set to default.
  If this MIB is set to forceDisable(1), the MTA will ignore the configuration file and disable Caller ID in
   Call Waiting scenarios.  The persistent value will be set to forceDisable(1).  On subsequent MTA
   Registrations, Caller ID will continue to be disabled in Call Waiting scenarios.
  If this MIB is set to forceEnable(2), the MTA will ignore the configuration file, and enable Caller ID in
   Call Waiting scenarios.  The persistent value will be set to forceEnable(1).  On subsequent MTA
   registrations Caller ID will continue to be enabled in Call Waiting scenarios."
 ::= { sipCfgPortEntry 28 }

sipCfgDigitMap OBJECT-TYPE
 SYNTAX OCTET STRING (SIZE (0..2048))
 MAX-ACCESS read-write
 STATUS current
 DESCRIPTION
  "This table is used to define digit map for the device.  The format of
   the string is the same as a digit map used in MGCP.  It is only
   settable in the config file. This object is only settable during config
   file download."
 ::= { sipConfiguration 2 }

sipCfgProxyAdr OBJECT-TYPE
 SYNTAX DisplayString
 MAX-ACCESS read-write
 STATUS current
 DESCRIPTION
  "This is the address of the SIP proxy server.  This can be the same server
   as the registrar server. This    object is only settable during config file
   download."
 ::= { sipConfiguration 3 }

sipCfgProxyType OBJECT-TYPE
 SYNTAX INTEGER{
                ipv4(0),
                dns(1),
                unknown(2)}
 MAX-ACCESS read-write
 STATUS current
 DESCRIPTION
  "This is the type of the SIP proxy server. This object is only settable during
   config file download."
 ::= { sipConfiguration 4 }

sipCfgRegistrarAdr OBJECT-TYPE
 SYNTAX DisplayString
 MAX-ACCESS read-write
 STATUS current
 DESCRIPTION
  "This is the address of the SIP registrar server, this can be the same
   server as the proxy server. This object is only settable during config
   file download."
 ::= { sipConfiguration 5 }

sipCfgRegistrarType OBJECT-TYPE
 SYNTAX INTEGER{
                ipv4(0),
                dns(1)}
 MAX-ACCESS read-write
 STATUS current
 DESCRIPTION
  "This is the type of the SIP registrar server. This object is only settable
   during config file download."
 ::= { sipConfiguration 6 }

sipCfgSipFeatureSwitch OBJECT-TYPE
  SYNTAX BITS {
      telUriScheme(0),
      mtaFQDN(1),
      mwiRFC3842(2),
      advFlashFeatures(3),
      rfc3323Privacyheader(4),
      overrideDomain(5),
      disableCwCid(6),
      useIpAddressOf0ForHold(7),
      disable100REL(8),
      useSrvLookups(9),
      rtpKeepAlive(10),
      ignoreEarlyMedia(11),
      hookflashViaInfo(12),
      limitSdpUpdates(13),
      generateRemoteRT(14),
      playLocalRtAfterEarlyMedia(15),
      removeAuthHeaders(16),
      useInactiveMedia(17),
      noProvisionalSdpIn1XX(18),
      disconnectOtherCallOnEmergency(19),
      proxyPenaltyBox(20),
      playBusyToneOnReject(21),
      sessionTimerReInvite(22),
      emergencyOnhookSendBye(23),
      disableSessionTimers(24),
      stutterToneHookFlash(25),
      hookflashViaInfoStd(26),
      subscribeUAProfileXML(27),
      subscribeRegEventXML(28),
      preferTelUriForCid(29),
      callHoldWithoutReInvite(30),
      restrictIncomingOffer(31)
  }
  MAX-ACCESS read-write
  STATUS current
  DESCRIPTION
    "This object is used to enable features of the Arris SIP MTA. From left to
     right, the specified bit indicates whether or not the corresponding feature
     is enabled.  For example, if the first bit is set, then the telUriScheme
     feature is enabled. If it is zero, the feature is disabled.  NO bits are
     set by default.

     /** BIT Descriptions **/
     0x80000000 : telUriScheme       - Use tel Uri Scheme 'tel:' (currently unsupported).
     0x40000000 : mtaFQDN            - Use MTA's local FQDN instead of local IP.
     0x20000000 : mwiRFC3842         - Use RFC3842 for MWI (message waiting indicator).
     0x10000000 : advFlashFeatures   - Enable Advanced Flash Features.
     0x08000000 : rfc3323Privacyheader - Use RFC 3323 defined privacy header for caller id blocking.
     0x04000000 : overrideDomain     - Override the domain value in outgoing messages with the proxy setting.
     0x02000000 : disableCwCid       - Disable the use of caller-id during call waiting.
     0x01000000 : useIpAddressOf0ForHold - Use an IP address of 0.0.0.0 and port of 0 in SDP instead of a=sendonly for hold.
     0x00800000 : disable100REL      - This is set if we DO NOT want to advertise that we support 100rel (must be set in MTA config file).
     0x00400000 : useSrvLookups      - This bit is set if we want to use SRV lookups for the server addresses (must be set in the MTA config file).
     0x00200000 : rtpKeepAlive       - With this bit set the endpoint will send silent packets over a held connection
     0x00100000 : ignoreEarlyMedia   - This bit is set if we want to ignore all media received before the remote SDP is obtained.
     0x00080000 : hookflashViaInfo   - With this bit set the endpoint will signal hookflash via an info message instead of locally processing it -- BoradSoft method
     0x00040000 : limitSdpUpdates    - With this bit set, we will scan over new SDPs we generate to only increment the origin line if critical info has changed.
     0x00020000 : generateRemoteRT   - This bit is set if we want to generate ringback tone over the connection.
     0x00010000 : playLocalRtAfterEarlyMedia - This bit is set to play local RT upon receipt of a 180 after early media is detected.
     0x00008000 : removeAuthHeaders  - This bit is set to remove the unneeded auth headers from a callLeg after a 401 or 407 response is received.
     0x00004000 : useInactiveMedia   - This bit is set to allow the MTA to hold calls using the INACTIVE media attribute.
     0x00002000 : noProvisionalSdpIn1XX - This bit is set to turn off sending early media (SDP in provisional 1XX response) on incoming INVITEs with 100Rel enabled
     0x00001000 : disconnectOtherCallOnEmergency - Disconnect the other call in the connection when there is an incoming or outgoing emergency call.
     0x00000800 : proxyPenaltyBox    - Use penalty box for unresponsive proxies
     0x00000400 : playBusyToneOnReject  - This bit is set to always play busy tone when an outbound call is rejected
     0x00000200 : sessionTimerReInvite  - Use Re-INVITE instead of UPDATE for session timer refresh
     0x00000100 : emergencyOnhookSendBye  -  With this bit set, BYE message will be sent after an emergency call goes on-hook
     0x00000080 : disableSessionTimers - Do not use SIP Session Timers (RFC 4028).This setting will only take effect after an MTA reset or full reset because it requires that the SIP stack be restarted.
     0x00000040 : stutterToneHookFlash - With this bit set, stutter dial tone will be played when hook is flashed for a second call.
     0x00000020 : hookflashViaInfoStd  - With this bit set the endpoint will signal hookflash via an info message instead of locally processing it -- Standard method
     0x00000010 : subscribeUAProfileXML   - subscribe to UA Profile event package, application XML, including Call Forward count
     0x00000008 : subscribeRegEventXML   - Subscribe to reg event package, application XML
     0x00000004 : preferTelUriForCid      - Use TEL-URI as precedence over SIP-URI  for Caller ID display
     0x00000002 : callHoldWithoutReInvite.   - With this bit set,the call hold will be processed locally instead of sending out reinvite
     0x00000001 : restrictIncomingOffer   - Use the provisioned SIP Codec Array to restrict an incoming offer"
  DEFVAL { '00000000'h }
 ::= { sipConfiguration 7 }

sipCfgProvisionedCodecArray OBJECT-TYPE
 SYNTAX DisplayString
 MAX-ACCESS read-write
 STATUS current
 DESCRIPTION
  "This is the list of codecs offered in the OFFER SDP. The order
   of this list is also the order of preference used in the OFFER SDP.
   These are entered as a string separated by semi-colon ';' for example
   'PCMU;PCMA;G726-32;telephone-event'

   The supported codecs are PCMU, PCMA, G728, G729, G729E, G726-16,
   G726-24, G726-32, G726-40, telephone-event.

   The default string will be 'PCMU;PCMA'. This object is only settable
   during config file download."
 ::= { sipConfiguration 8 }

sipCfgPacketizationRate OBJECT-TYPE
 SYNTAX INTEGER{
                tenMilliSeconds(10),
                twentyMilliSeconds(20),
                thirtyMilliSeconds(30)}
 MAX-ACCESS read-write
 STATUS current
 DESCRIPTION
  "RTP Packetization Rate. This object is only settable during config file
   download."
 DEFVAL { twentyMilliSeconds }
 ::= { sipConfiguration 9 }

sipCfgDialFeatMap OBJECT-TYPE
 SYNTAX OCTET STRING (SIZE (0..2048))
 MAX-ACCESS read-write
 STATUS current
 DESCRIPTION
  "This defines the dialed digits on a handset to the actual dialing feature.
   It allows for 3 aliases per feature separated by commas followed by the dialing
   feature name. A pipe is used to designate the end of the assignment. An example
   would be:

   *70,1170, ,CALWD|*67,1167, ,CIDTB|*77,1177, ,ANNCJ|*87,1187, ,ANCJD|*65,1165, ,CIDPB|
   *82,1182, ,CIDTE|

   CALWD = Call Waiting Disable
   CIDTB = Caller ID Temp Block
   CIDPB = Caller ID Perm Block
   CIDTB = Caller ID Temp Block
   ANNCJ = Anonymous Call Rejection
   ANCJD = Anonymous Call Rejection Disable

   This example two of the settings are dialing *70 or 1170 will disable call waiting and
   *67 or 1167 will temporarily block caller ID for that one call. This object is only
   settable during config file download."
 ::= { sipConfiguration 10 }

sipCfgDialFeatTable OBJECT-TYPE
 SYNTAX SEQUENCE OF SipCfgDialFeatEntry
 MAX-ACCESS not-accessible
 STATUS current
 DESCRIPTION
  "This table is used to define the SIP configurable data on a per port basis."
 ::= { sipConfiguration 11 }

sipCfgDialFeatEntry OBJECT-TYPE
 SYNTAX SipCfgDialFeatEntry
 MAX-ACCESS not-accessible
 STATUS current
 DESCRIPTION
  "An entry in the Configuration Feature table."
 INDEX { sipCfgDialFeatNumber }
 ::= { sipCfgDialFeatTable 1 }

SipCfgDialFeatEntry ::= SEQUENCE{
  sipCfgDialFeatNumber  Integer32,
  sipCfgDialFeatName    INTEGER,
  sipCfgDialFeatCode    DisplayString,
  sipCfgDialFeatTone    INTEGER,
  sipCfgDialFeatActive  BITS,
  sipCfgDialFeatMode    BITS
 }

sipCfgDialFeatNumber OBJECT-TYPE
 SYNTAX Integer32
 MAX-ACCESS not-accessible
 STATUS current
 DESCRIPTION
  "The unique value which identifies the feature."
 ::= { sipCfgDialFeatEntry 1 }


sipCfgDialFeatName OBJECT-TYPE
 SYNTAX INTEGER{
                anonCallReject(1),
                anonCallRejectDisable(2),
                callForwardBusy(30),
                callForwardBusyDisable(31),
                callForwardUncond(32),
                callForwardUncondDisable(33),
                callForwardNoAnswer(34),
                callForwardNoAnswerDisable(35),
                warmline(36),
                warmlineDisable(37),
                callReturn(50),
                callReDial(60),
                callHold(61),
                repeatDialingEnable(62),
                repeatDialingCancel(63),
                callWaitTempDisable(70),
                callWaitPermDisableToggle(71),
                callWaitPermanentDisable(72),
                callWaitPermanentEnable(73),
                callerIDPermBlockToggle(90),
                callerIDTempEnable(91),
                callerIDTempBlock(92)}
 MAX-ACCESS read-write
 STATUS current
 DESCRIPTION
  "Table of supported calling features."
 ::= { sipCfgDialFeatEntry 2 }

sipCfgDialFeatCode OBJECT-TYPE
 SYNTAX DisplayString
 MAX-ACCESS read-write
 STATUS current
 DESCRIPTION
  "String comma separated to specify up to three codes for a particular feature.
   Example:

   *70,1170,*71

   This would specify that either *70, 1170 or *71 would activate the current
   feature.  A maximum of three values are supported."
 ::= { sipCfgDialFeatEntry 3 }

sipCfgDialFeatTone OBJECT-TYPE
 SYNTAX INTEGER{
                stutterTone(1),
                dialTone(2)}
 MAX-ACCESS read-write
 STATUS current
 DESCRIPTION
  "This allows specification of a tone to be applied when a feature is entered.
   Typically stutter tone is used to acknowledge a feature was entered but this can
   be redefined here."
 ::= { sipCfgDialFeatEntry 4 }


sipCfgDialFeatActive OBJECT-TYPE
  SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
  }
 MAX-ACCESS read-write
 STATUS current
 DESCRIPTION
  "This allows a particular feature to be enabled or disabled based on a particular line number.

   Example a setting of 0x0003 would have this feature enabled for line 1 and line 2."
 ::= { sipCfgDialFeatEntry 5 }

sipCfgDialFeatMode OBJECT-TYPE
    SYNTAX BITS {
    unused0(0),
    unused1(1),
    unused2(2),
    unused3(3),
    unused4(4),
    unused5(5),
    busy(6),
    initialDialing(7)
}
MAX-ACCESS read-write
STATUS current
DESCRIPTION
  "This allows a particular feature to be enabled in different modes of dialing.  The default is
   a setting of 0x1 where the feature is active in a initial dialing (normal)"
  ::= { sipCfgDialFeatEntry 6 }


sipCfgDialProxyMap OBJECT-TYPE
 SYNTAX OCTET STRING (SIZE (0..2048))
 MAX-ACCESS read-write
 STATUS current
 DESCRIPTION
  "This defines the dialed digits on a handset to the actual dialing feature that is to
   be handled by a SIP Proxy.

   It allows a dial code, a specified tone and the line bitmap.
   A pipe is used to designate the end of the assignment. An example
   would be:

   code, tone, active |

   *50,1,3|*93,2,0|

   code   = the dial sequence for the fature on the SIP Proxy
   tone   = the specific tone to be played when dialed
   active = is a UINT32 bitmask with each bit representing which line has this feature

   tone: 1 = studder dialtone, 2 = dialtone

   This example has two features.  The first is when *50 is dialed tone number 1 will be
   played and the feature is actived on line 1 and line 2 (000 0011).

   The second feature is *93 that when dialed would issue a dialtone.  However there are
   no active bits set so no lines on this box will offer this feature so it is currently
   disabled.

   NOTE: This MIB is loaded by TLV43/TLV71."
 ::= { sipConfiguration 12 }

sipCfgAlertInfoR0 OBJECT-TYPE
 SYNTAX DisplayString (SIZE (0..50))
 MAX-ACCESS read-write
 STATUS current
 DESCRIPTION
  "This is the string that will be used as the value of the Alert-Info header field
   to instruct the MTA to play either the R0 Ringing Cadence.  Note that there is
   not a WT0 waiting tone that corresponds to this header."
 ::= { sipConfiguration 13 }

sipCfgAlertInfoR1 OBJECT-TYPE
 SYNTAX DisplayString (SIZE (0..50))
 MAX-ACCESS read-write
 STATUS current
 DESCRIPTION
  "This is the string that will be used as the value of the Alert-Info header field
   to instruct the MTA to play either the R1 Ringing Cadence or the WT1 call waiting
   tone depending on if a call is active."
 ::= { sipConfiguration 14 }

sipCfgAlertInfoR2 OBJECT-TYPE
 SYNTAX DisplayString (SIZE (0..50))
 MAX-ACCESS read-write
 STATUS current
 DESCRIPTION
  "This is the string that will be used as the value of the Alert-Info header field
   to instruct the MTA to play either the R2 Ringing Cadence or the WT2 call waiting
   tone depending on if a call is active."
 ::= { sipConfiguration 15 }

sipCfgAlertInfoR3 OBJECT-TYPE
 SYNTAX DisplayString (SIZE (0..50))
 MAX-ACCESS read-write
 STATUS current
 DESCRIPTION
  "This is the string that will be used as the value of the Alert-Info header field
   to instruct the MTA to play either the R3 Ringing Cadence or the WT3 call waiting
   tone depending on if a call is active."
 ::= { sipConfiguration 16 }

sipCfgAlertInfoR4 OBJECT-TYPE
 SYNTAX DisplayString (SIZE (0..50))
 MAX-ACCESS read-write
 STATUS current
 DESCRIPTION
  "This is the string that will be used as the value of the Alert-Info header field
   to instruct the MTA to play either the R4 Ringing Cadence or the WT4 call waiting
   tone depending on if a call is active."
 ::= { sipConfiguration 17 }

sipCfgAlertInfoR5 OBJECT-TYPE
 SYNTAX DisplayString (SIZE (0..50))
 MAX-ACCESS read-write
 STATUS current
 DESCRIPTION
  "This is the string that will be used as the value of the Alert-Info header field
   to instruct the MTA to play either the R5 Ringing Cadence.  Note that there is
   not a WT5 waiting tone that corresponds to this header."
 ::= { sipConfiguration 18 }

sipCfgAlertInfoR6 OBJECT-TYPE
 SYNTAX DisplayString (SIZE (0..50))
 MAX-ACCESS read-write
 STATUS current
 DESCRIPTION
  "This is the string that will be used as the value of the Alert-Info header field
   to instruct the MTA to play either the R6 Ringing Cadence.  Note that there is
   not a WT6 waiting tone that corresponds to this header."
 ::= { sipConfiguration 19 }

sipCfgAlertInfoR7 OBJECT-TYPE
 SYNTAX DisplayString (SIZE (0..50))
 MAX-ACCESS read-write
 STATUS current
 DESCRIPTION
  "This is the string that will be used as the value of the Alert-Info header field
   to instruct the MTA to play either the R7 Ringing Cadence.  Note that there is
   not a WT7 waiting tone that corresponds to this header."
 ::= { sipConfiguration 20 }

sipCfgDomainOverride OBJECT-TYPE
 SYNTAX DisplayString
 MAX-ACCESS read-write
 STATUS current
 DESCRIPTION
  "This is the string that will be used as the value of the domain in all outbound
   SIP signalling messages.  This can only be set in the configuration file"
 ::= { sipConfiguration 21 }

 sipCfgEmergencyNumber OBJECT-TYPE
 SYNTAX DisplayString (SIZE (0..50))
 MAX-ACCESS read-write
 STATUS current
 DESCRIPTION
  "This is the string that will specify the emergency number.  A call to an emergency # cannot
   be pre-empted.  If a three way call is attempted with an emergency # the other call is terminated.
   Flash, OnHook have no effect during an emergency call."
 ::= { sipConfiguration 22 }

  sipCfgRegTimerMin OBJECT-TYPE
 SYNTAX Integer32
 MAX-ACCESS read-write
 STATUS current
 DESCRIPTION
  "This integer specifies the minimum registration retry interval (in seconds)"
 ::= { sipConfiguration 23 }

   sipCfgRegTimerMax OBJECT-TYPE
 SYNTAX Integer32
 MAX-ACCESS read-write
 STATUS current
 DESCRIPTION
  "This integer specifies the maximum registration retry interval (in seconds)"
 ::= { sipConfiguration 24 }

sipStatusPortTable OBJECT-TYPE
 SYNTAX SEQUENCE OF SipStatusPortEntry
 MAX-ACCESS not-accessible
 STATUS current
 DESCRIPTION
  "This table is used to get SIP status data on a per port basis."
 ::= { sipStatus 1 }

sipStatusPortEntry OBJECT-TYPE
 SYNTAX SipStatusPortEntry
 MAX-ACCESS not-accessible
 STATUS current
 DESCRIPTION
  "An entry in the Status Port table."
 INDEX { sipStatusPortPortNumber }
 ::= { sipStatusPortTable 1 }

SipStatusPortEntry ::= SEQUENCE{
  sipStatusPortPortNumber Integer32,
  sipStatusAlarms BITS,
  sipStatusPortMWISubscribed TruthValue
}

sipStatusPortPortNumber OBJECT-TYPE
 SYNTAX Integer32
 MAX-ACCESS not-accessible
 STATUS current
 DESCRIPTION
  "The unique value which identifies the port."
 ::= { sipStatusPortEntry 1 }

 sipStatusAlarms OBJECT-TYPE
  SYNTAX BITS
  {
      unused(0),
      generalErrorAlrm(1),
      networkErrorAlrm(2),
      callLegSentAuth(3),
      regClientSentAuthReq(4),
      authFailAlrm(5),
      registrarLocAlrm(6),
      proxyLocAlrm(7)
}
MAX-ACCESS read-only
    STATUS current
    DESCRIPTION
          "This MIB object reports the current SIP alarm state for each line.

           generalErrorAlrm - set when an error occurs that doesn't have an
           RFC supported error condition

           networkErrorAlrm - set when a network error occurs such as DNS failure
           or ICMP destination unreachable

           callLegSentAuth - set when the callLeg has sent authorization information
           due to a authorization required response

           regClientSentAuthReq - set when the registration client has sent
           authorization information due to a authorization required response

           authFailAlrm - set when authentication failed during registration or callLeg
           authorization after authorization information was sent

           registrarLocAlrm - set by the register client when REGISTER messages timeout
           (Loss of communications)

           proxyLocAlrm - set when CallLeg messages timeout (Loss of communications)"
 ::= {sipStatusPortEntry 2}

sipStatusPortMWISubscribed OBJECT-TYPE
 SYNTAX TruthValue
 MAX-ACCESS read-only
 STATUS current
 DESCRIPTION
  "This MIB indicates MWI is subscribed or not."
 ::= { sipStatusPortEntry 3 }

sipCfgT1 OBJECT-TYPE
 SYNTAX Integer32
 MAX-ACCESS read-write
 STATUS current
 DESCRIPTION
  "This integer specifies the minimum wait time between retransmission for SIP outgoing calls(T1 in RFC 3261)."
 ::= { sipConfiguration 25 }

sipCfgMaxRetrans OBJECT-TYPE
 SYNTAX Integer32
 MAX-ACCESS read-write
 STATUS current
 DESCRIPTION
  "DEPRECATED - Please use sipCfgTimerB.  This integer specifies the number of transmit attempts that will be made on an outgoing INVITE message"
 ::= { sipConfiguration 26 }

sipCfgMediaLoopbackNumber OBJECT-TYPE
 SYNTAX DisplayString (SIZE (0..50))
 MAX-ACCESS read-write
 STATUS current
 DESCRIPTION
  "This string specifies the number for media loopback.  If an incoming call comes from this number the MTA
   will treat the call as if it is a loopback call.  The phone will not ring and the call will be auto-
   answered."
 ::= { sipConfiguration 27 }

sipCfgPacketLoopbackNumber OBJECT-TYPE
 SYNTAX DisplayString (SIZE (0..50))
 MAX-ACCESS read-write
 STATUS current
 DESCRIPTION
  "This string specifies the number for packet loopback.  If an incoming call comes from this number the MTA
   will treat the call as if it is a loopback call.  The phone will not ring and the call will be auto-
   answered."
 ::= { sipConfiguration 28 }

sipCfgBusyDigitMap OBJECT-TYPE
 SYNTAX OCTET STRING (SIZE (0..2048))
 MAX-ACCESS read-write
 STATUS current
 DESCRIPTION
  "This table is used to define digit map for the device while busy tone is being played.  The format of
   the string is the same as a digit map used in MGCP.  It is only
   settable in the config file."
 ::= { sipConfiguration 29 }

sipCfgRepeatDialingInterval OBJECT-TYPE
 SYNTAX Integer32
 MAX-ACCESS read-write
 STATUS current
 DESCRIPTION
  "This integer specifies the time between repeat dialing attempts for the repeat dialing feature.  This
   integer is represented as seconds. It is only settable in the config file."
 ::= { sipConfiguration 30 }

sipCfgRepeatDialingTimeout OBJECT-TYPE
 SYNTAX Integer32
 MAX-ACCESS read-write
 STATUS current
 DESCRIPTION
  "This integer specifies the length of time that the repeat dialing feature will retry.  After this timer
   elapses no more retry attempts will be made.  The timer is started when the feature code for repeat dialing
   is entered. It is only settable in the config file."
 ::= { sipConfiguration 31 }

sipCfgRepeatDialingSessionProgressTimer OBJECT-TYPE
 SYNTAX Integer32
 MAX-ACCESS read-write
 STATUS current
 DESCRIPTION
  "This integer specifies the length of time after a 183 is received before considering the repeat dialing attempt
   successful.  Often a 183 will be received prior to a negative response.  This timer prevents false positives
   It is only settable in the config file."
 ::= { sipConfiguration 32 }

sipCfgFeatureCapability OBJECT IDENTIFIER ::= {sipConfiguration 33}

sipCfgCallerIdDisplayCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to display caller ID"
 ::= {sipCfgFeatureCapability 1}


sipCfgCallerIdSendCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to send caller ID"
 ::= {sipCfgFeatureCapability 2}


sipCfgAnonCallRejectionCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to reject anonymous calls"
 ::= {sipCfgFeatureCapability 3}


sipCfgCallWaitingCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to have call waiting"
 ::= {sipCfgFeatureCapability 4}


sipCfgThreeWayCallCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to do three way calling"
 ::= {sipCfgFeatureCapability 5}


sipCfgCallTransferCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to transfer calls"
 ::= {sipCfgFeatureCapability 6}


sipCfgCallForwardCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to forward calls"
 ::= {sipCfgFeatureCapability 7}


sipCfgCallReturnCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to return calls"
 ::= {sipCfgFeatureCapability 8}


sipCfgCallRedialCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to redial last number (as a dial feature)"
 ::= {sipCfgFeatureCapability 9}


sipCfgCallHoldCapability OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
 "MSO-defined capability of each line to hold calls"
 ::= {sipCfgFeatureCapability 10}

sipCfgProxyDigitMap OBJECT-TYPE
 SYNTAX OCTET STRING (SIZE (0..2048))
 MAX-ACCESS read-write
 STATUS current
 DESCRIPTION
  "This table is used to define the digit map for the device after dialing
  a star code that matches the proxy map.  The format of the string is the
  same as a digit map used in MGCP.  It is only settable in the config
  file. Its default value is 'x.[t#]' "
 ::= { sipConfiguration 34 }

 sipCfgCallWaitingStarCodeSurvivesReset OBJECT-TYPE
 SYNTAX INTEGER{ false(1),
                 true(2) }
 MAX-ACCESS read-write
 STATUS current
 DESCRIPTION
  "An NVM setting has been added that stores the state of Call Waiting Permanent Disabled so that the state
   survives a reset.  This MIB enables the storage of the Call Waiting state in NVM.  Some customers will want
   to leave this MIB at a default value of 0 because of the following scenario:
   1.   MSO issues a modem to end user A
   2.   A dials star code to disable call waiting
   3.   MSO reclaims modem
   4.   MSO issues the modem to end user B
   5.   B does not know why call waiting does not work.

   Values:
      1 - Call Waiting Permanent Disable state is NOT stored in NVM, and Call Waiting returns to MSO defined default settings
          when a reset occurs. If neither sipCfgCallWaitingCapability nor sipCfgPortFeatureSettings is defined in the MTA
          configuration file, then Call Waiting will be enabled at reset.
      2 - If the end user dials a dial code to disable call waiting, that setting will survive resets and will last until one
          of the following events occurs: end user dials a dial code to enable call waiting,  or sipCfgResetCallWaitingStarCode MIB is
          used via SNMP.

   This MIB can only be set via the MTA configuration file."
 ::= { sipConfiguration 35 }

 sipCfgResetCallWaitingStarCode OBJECT-TYPE
 SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
 }
 MAX-ACCESS read-write
 STATUS current
 DESCRIPTION
  "This MIB is intended for use by the MSO to enable call waiting via SNMP if they have sipCfgCallWaitingDisableSurvivesReset
   set to 1 and the following happens:
   1.   MSO issues a modem to end user A
   2.   A dials star code to disable call waiting
   3.   MSO reclaims modem
   4.   MSO issues the modem to end user B
   5.   B does not know why call waiting does not work.

   This MIB can be used to clear the NVM setting for call waiting disable since a reset will not clear it if the MTA
   configuration file specifies a sipCfgCallWaitingDisableSurvivesReset of 1.

   Usage:
      Hexadecimal bit string where each bit represents a different phone line (starting with line 1 on the least significant
      bit).  The bit string specifies for which lines to reset the NVM Call Waiting setting to its default value of enabled.
      If a bit is set to 1, that line's NVM Call Waiting setting is returned to default.  If a bit is set to 0, nothing is
      done to that line.

   EXAMPLE:
      To return call waiting to factory default setting for all lines, set sipCfgResetCallWaitingStarCode to FFFFFFFF.
      To reset the setting for line  1 only, set sipCfgResetCallWaitingStarCode to 00000001.
      To reset the setting for line 12 only, set sipCfgResetCallWaitingStarCode to 00000800.

      When reclaiming a modem from one end user and issuing it to another, if sipCfgCallWaitingDisableStarCodeSurvivesReset
      was set to true in the config file, then it is advisable to set sipCfgResetCallWaitingStarCode to FFFFFFFF via SNMP
      before giving the modem to the new user."
 ::= { sipConfiguration 36 }

sipCfgDialProxyTable OBJECT-TYPE
 SYNTAX SEQUENCE OF SipCfgDialProxyEntry
 MAX-ACCESS not-accessible
 STATUS current
 DESCRIPTION
  "This table replaces an older MIB, sipCfgDialProxyMap, and defines the dial features
   that are handled by the proxy."
 ::= { sipConfiguration 37 }

sipCfgDialProxyEntry OBJECT-TYPE
 SYNTAX SipCfgDialProxyEntry
 MAX-ACCESS not-accessible
 STATUS current
 DESCRIPTION
  "An entry in the Configuration Feature table."
 INDEX { sipCfgDialProxyNumber }
 ::= { sipCfgDialProxyTable 1 }

SipCfgDialProxyEntry ::= SEQUENCE{
  sipCfgDialProxyNumber  Integer32,
  sipCfgDialProxyCode    DisplayString,
  sipCfgDialProxyTone    INTEGER,
  sipCfgDialProxyActive  BITS,
  sipCfgDialProxyMessageType    INTEGER,
  sipCfgDialProxyMethod INTEGER,
  sipCfgDialProxyMethodDelimiter  DisplayString
 }

sipCfgDialProxyNumber OBJECT-TYPE
 SYNTAX Integer32
 MAX-ACCESS not-accessible
 STATUS current
 DESCRIPTION
  "The unique value which identifies the feature."
 ::= { sipCfgDialProxyEntry 1 }


sipCfgDialProxyCode OBJECT-TYPE
 SYNTAX DisplayString
 MAX-ACCESS read-write
 STATUS current
 DESCRIPTION
  "The dial code that activates this feature.  For example, *70"
 ::= { sipCfgDialProxyEntry 2 }

sipCfgDialProxyTone OBJECT-TYPE
 SYNTAX INTEGER{
                stutterTone(1),
                dialTone(2)}
 MAX-ACCESS read-write
 STATUS current
 DESCRIPTION
  "This allows specification of a tone to be applied when a feature is entered.
   Typically stutter tone is used to acknowledge a feature was entered but this can
   be redefined here."
 ::= { sipCfgDialProxyEntry 3 }


sipCfgDialProxyActive OBJECT-TYPE
  SYNTAX BITS {
      line32(0),
      line31(1),
      line30(2),
      line29(3),
      line28(4),
      line27(5),
      line26(6),
      line25(7),
      line24(8),
      line23(9),
      line22(10),
      line21(11),
      line20(12),
      line19(13),
      line18(14),
      line17(15),
      line16(16),
      line15(17),
      line14(18),
      line13(19),
      line12(20),
      line11(21),
      line10(22),
      line09(23),
      line08(24),
      line07(25),
      line06(26),
      line05(27),
      line04(28),
      line03(29),
      line02(30),
      line01(31)
  }
 MAX-ACCESS read-write
 STATUS current
 DESCRIPTION
  "This allows a particular feature to be enabled or disabled based on a particular line number.

   Example a setting of 0x0003 would have this feature enabled for line 1 and line 2."
 ::= { sipCfgDialProxyEntry 4 }

sipCfgDialProxyMessageType OBJECT-TYPE
 SYNTAX INTEGER{
                invite(1),
                refer(2)}
MAX-ACCESS read-write
STATUS current
DESCRIPTION
  "For most proxy dial features, an INVITE message is sent to the proxy.
   In special cases, a REFER message should be sent."
  ::= { sipCfgDialProxyEntry 5 }

sipCfgDialProxyMethod OBJECT-TYPE
    SYNTAX INTEGER{
         default(0),
         pc20(1)
    }
    MAX-ACCESS read-write
    STATUS current
    DESCRIPTION
    "Used to configure the method that the VSC is passed up to the proxy.
     In the 'default' method the VSC is prepended to the dialstring and sent to
     the proxy.  In the 'PC20' method the VSC is sent as the host of the SIP URI
     the dialstring is then sent to the proxy in a user parameter in the SIP URI."
 ::= { sipCfgDialProxyEntry 6 }

sipCfgDialProxyMethodDelimiter OBJECT-TYPE
 SYNTAX DisplayString
 MAX-ACCESS read-write
 STATUS current
 DESCRIPTION
  "Used to define the delimiter between the VSC and the number in the SIP INVITE message.
   If this mib is not set, a '.' will be used as the delimiter.
   The max length of delimiter is 4.

   This mib is valid only if sipCfgDialProxyMethod is set to 'pc20'."
 ::= { sipCfgDialProxyEntry 7 }

sipCfgDhcp60AnnouncementMode OBJECT-TYPE
     SYNTAX INTEGER {
         disable(0),
         enable(1)
     }
     MAX-ACCESS read-write
     STATUS current
     DESCRIPTION
        "Used to enable/disable SIP advertisement in MTA DHCP Option60.
         This MIB can only be set via the CM configuration file."
 ::= { sipConfiguration 38 }

sipCfgCallForwardForbiddenNumbers OBJECT-TYPE
    SYNTAX DisplayString (SIZE (0..50))
    MAX-ACCESS read-write
    STATUS current
    DESCRIPTION
        "There are certain phone numbers (eg 911) that Call Forwarding should
        not accept as forwarding numbers.  This MIB specifies which numbers
        are not allowed as forwarding numbers.  This MIB is only settable via
        config file. Multiple numbers may be specified separated by | as follows:

        911|900|1900|0

        Note: the emergency number set in sipCfgEmergencyNumber is also not allowed
        as a forwarding number."
 ::= { sipConfiguration 39 }

sipCfgDefaultG711 OBJECT-TYPE
 SYNTAX INTEGER{
                pcmu(0),
                pcma(8)}
 MAX-ACCESS read-write
 STATUS current
 DESCRIPTION
  "RTP Default Voice or pass-thru codec. This object is only settable during config file
   download."
 DEFVAL { pcmu }
 ::= { sipConfiguration 40 }

sipCfgGenLinger OBJECT-TYPE
 SYNTAX Integer32
 MAX-ACCESS read-write
 STATUS current
 DESCRIPTION
  "This integer specifies the wait time in milliseconds for response retransmits (non-INVITE) (Timer K in RFC 3261)."
 ::= { sipConfiguration 41 }

sipCfgInviteLinger OBJECT-TYPE
 SYNTAX Integer32
 MAX-ACCESS read-write
 STATUS current
 DESCRIPTION
  "This integer specifies the wait time in milliseconds for response retransmits (INVITE) and the wait time for ACK receipt (Timers D and H in RFC 3261)."
 ::= { sipConfiguration 42 }

sipCfgTimerB OBJECT-TYPE
 SYNTAX Integer32
 MAX-ACCESS read-write
 STATUS current
 DESCRIPTION
  "This integer specifies the INVITE transaction timeout timer in seconds(Timer B in RFC 3261)."
 ::= { sipConfiguration 43 }

sipCfgTimerF OBJECT-TYPE
 SYNTAX Integer32
 MAX-ACCESS read-write
 STATUS current
 DESCRIPTION
  "This integer specifies the non-INVITE transaction timeout timer in seconds(Timer F in RFC 3261)."
 ::= { sipConfiguration 44 }

sipCfgRegExpires OBJECT-TYPE
 SYNTAX Integer32
 MAX-ACCESS read-write
 STATUS current
 DESCRIPTION
  "This integer specifies the preferred registration expiry value (in seconds) sent in the REGISTER message.
   If unspecified or the value is set to zero, no expiry value is preferred and none will be sent to
   the registrar."
 ::= { sipConfiguration 45 }

sipCfgMaxUDPSize OBJECT-TYPE
 SYNTAX Integer32
 MAX-ACCESS read-write
 STATUS current
 DESCRIPTION
  "This integer specifies the threshold at which point packets will begin being sent over TCP rather than UDP.
   When set to zero, no threshold exists and all packets will be sent using UDP. It is for the SIP request
   message only.
   In TS6.1 this MIB defaults to zero (UDP is always used by default).
   In TS6.2 this MIB defaults to 1300."
 ::= { sipConfiguration 46 }

sipCfgSessionExpires OBJECT-TYPE
 SYNTAX Integer32
 MAX-ACCESS read-write
 STATUS current
 DESCRIPTION
  "This integer specifies the preferred session expiry value (in seconds) sent in the INVITE message.
   This value defaults to 1800 and the minimum value is 0."
 ::= { sipConfiguration 47 }

sipCfgPenaltyBoxTimeout OBJECT-TYPE
 SYNTAX Integer32
 MAX-ACCESS read-write
 STATUS current
 DESCRIPTION
  "This integer specifies the timeout for entries in the SIP Proxy Penalty Box
   in HOURS. Default is 24 hours. Note that entries may be evicted from the
   Penalty Box before timeout if all known SRV records have failed to respond.
   This MIB is for legacy SIP only."
 ::= { sipConfiguration 48 }

sipCfgDisconnectReorderToneDelay OBJECT-TYPE
 SYNTAX Unsigned32 (0..180)
 MAX-ACCESS read-write
 STATUS current
 DESCRIPTION
  "This MIB Object specifies the delay between receiving BYE message and playing Disconnect Reorder Tone in seconds "
 DEFVAL { 5 }
 ::= { sipConfiguration 49 }

 sipCfgDistinctiveRingingForCallHold OBJECT-TYPE
 SYNTAX INTEGER{
                standard(0),
                r0(1),
                r1(2),
                r2(3),
                r3(4),
                r4(5),
                r5(6),
                r6(7),
                r7(8)
                }
 MAX-ACCESS read-write
 STATUS current
 DESCRIPTION
  "This is the type of distinctive ringing used when call is held"
 ::= { sipConfiguration 50 }

sipCfgSipFeatureSwitch2 OBJECT-TYPE
  SYNTAX BITS {
      pwdAutoGen(0),
      sipFailover(1),
      commonNonce(2),
      unused3(3),
      noRegOffhook(4),
      perLineImpi(5),
      dnsCache(6),
      optDstTimezone(7),
      rejectInviteWith480(8),
      perLineProxySelection(9),
      suppressTIASInSDP(10),
      addRouteHeaderToInitialRegMsg(11),
      dropInProgressCallsOnReregFailure(12),
      byeRejectedErrorHandling(13),
      strictMessageValidation(14),
      directStatsPublish(15),
      suppressUserphoneUrlParam(16),
      useDomainNameAsPcscfAddr(17),
      addPAccessNetworkInfoHeader(18),
      addPAccessNetworkInfoHeaderCancel(19),
      regUponNetworkRecovery(20),
      deregisterLineEnable(21),
      appendLocalIpAddressToCallid(22),
      sessionTimerNegotiationEnable(23),
      ignoreStandAloneMessage(24),
      addAuthHeaderAfterChallenge(25),
      hideRealTnInContactHeader(26),
      inviteErrorHandlingEnhancement(27),
      useDomainNameInRouteHeader(28),
      unsubMwiDuringFailover(29),
      serviceCapability(30),
      useMTAIpInContactHeader(31)
  }
  MAX-ACCESS read-write
  STATUS current
  DESCRIPTION
    "This object is like sipCfgSipFeatureSwitch. It is used to enable features of
     the Arris SIP MTA. From left to right, the specified bit indicates whether
     or not the corresponding feature is enabled/disabled.  For example, if the
     first bit is set, then the pwdAutoGen feature is enabled. If it is zero,
     the feature is disabled.  NO bits are set by default.

     /** BIT Descriptions **/
     0x80000000 : pwdAutoGen       - Auto-generate the SIP password.
     0x40000000 : sipFailover      - EDVA will failover to the secondary PCSCF when detect msg failure.
     0x20000000 : commonNonce      - Cache latest nonce for all outgoing messages.
     0x08000000 : noRegOffhook     - Don't try to register if user goes offhook when initial registration is not completed.
     0x04000000 : perLineImpi      - SIP password auto-generation generates per-line IMPIs.
     0x02000000 : dnsCache         - Use cached DNS records when receive negative response or no response.
     0x01000000 : optDstTimezone   - The timezone part of MIB pktcEUERSTCIDDisDSTInfo (PC20) or sipCfgCIDDisDSTInfo (Legacy SIP) is optional, CM learned timezone will be used if timezone not provided.
     0x00800000 : rejectInviteWith480 - If the line is disconnected from a call but remains off-hook, it rejects the incoming INVITE with 480 instead of 486.
     0x00400000 : perLineProxySelection - Each line contacts proxies with its own order.
     0x00200000 : suppressTIASInSDP - the Transport Independent Application Specific Maximum (TIAS) bandwidth modifier in SDP.
     0x00100000 : addRouteHeaderToInitialRegMsg - Add the route header to the initial register message.
     0x00080000 : dropInProgressCallsOnReregFailure - Unstable calls will be dropped on reregistration failure
     0x00040000 : byeRejectedErrorHandling - An additional BYE will be sent if an initial BYE is rejected by a non-407 response.
     0x00020000 : strictMessageValidation - Enable strict message validation check.
     0x00010000 : directStatsPublish - Publish the end-of-call stats directly to XR collector bypassing the proxy.
     0x00008000 : suppressUserphoneUrlParam - 'user=phone' in P-Preferred-Identity will be Suppressed
     0x00004000 : useDomainNameAsPcscfAddr - If PCSCF is not configured, domain name from DHCP will be used as PCSCF address.
     0x00002000 : addPAccessNetworkInfoHeader - P-Access-Network-Info header will be added to all the applicable outgoing SIP message.
     0x00001000 : addPAccessNetworkInfoHeaderCancel - If flag(0x00002000) of sip_ftr2 is enabled, P-Access-Network-Info header will be added to CANCEL and ACK related outgoing SIP message.
     0x00000800 : regUponNetworkRecovery - Try immediate registration once network is recovered.
     0x00000400 : deregisterLineEnable - if CM/MTA reset is determined, the EMTA will try to de-register each registerred line.
     0x00000200 : appendLocalIpAddressToCallid - Append the EMTA IP address to CALL-ID of SIP message.
     0x00000100 : sessionTimerNegotiationEnable - When it is enabled, the EMTA will not place 'refresher=uac' to the Session-Expires header of outgoing initial INVITE, and let the called party decide the refresher.
     0x00000080 : ignoreStandAloneMessage - If a SIP request is received but the number in Request-URI cannot be mapped to any line, EMTA will silently ignore it.
     0x00000040 : addAuthHeaderAfterChallenge - The Auth. header will be included in all subsequent SIP reuqest message(except CANCEL) after the outgoing INVITE has been challenged.
     0x00000020 : hideRealTnInContactHeader - Random string will be included in Contact header instead of the real TN.
     0x00000010 : inviteErrorHandlingEnhancement - enable invite error handling enhancement for 413 according to RFC3261 , an INVITE without SDP will be re-sent with the same CALLID as the former INVITE
     0x00000008 : useDomainNameInRouteHeader - With this bit set, domain name is used in route header of outgoing registration message when PCSCF type is DNS.
     0x00000004 : unsubMwiDuringFailover - With this bit set, if flag(0x40000000) of sip_ftr2 is enabled, EMTA will unsubscribe MWI when failover or failback is successful.
     0x00000002 : serviceCapability - With this bit set, Service Capability (RFC3840) will be enabled.
     0x00000001 : useMTAIpInContactHeader - With this bit set,Use MTA IP Address instead of '*' in Contact Header of De-REGISTER Message.
     "
  DEFVAL { '00000000'h }
 ::= { sipConfiguration 51 }

sipCfgAuthPasswordKey OBJECT-TYPE
 SYNTAX OCTET STRING(SIZE(0..32))
 MAX-ACCESS read-write
 STATUS current
 DESCRIPTION
  "This object is used for SIP password auto-generation feature."
 ::= { sipConfiguration 52 }


sipCfgMWITargetAddrType OBJECT-TYPE
 SYNTAX      InetAddressType
 MAX-ACCESS  read-write
 STATUS      current
 DESCRIPTION
  " This MIB Object specifies the address type for the MWI subscription target specified in sipCfgMWITargetAddr.
  If the element sipCfgMWITargetAddr contains a valid IP address,  this element MUST be 'ipv4(1)'."
 ::= { sipConfiguration 53 }

sipCfgMWITargetAddr OBJECT-TYPE
 SYNTAX InetAddress
 MAX-ACCESS read-write
 STATUS current
 DESCRIPTION
  "This MIB Object specifies the target address for the MWI subscription, and it is associated with the address
   type specified in sipCfgMWITargetAddrType."
 ::= { sipConfiguration 54 }

sipCfgMWITargetPort OBJECT-TYPE
 SYNTAX Unsigned32
 MAX-ACCESS read-write
 STATUS current
 DESCRIPTION
  "This MIB Object specifies the target port for the MWI subscription."
 DEFVAL { 5060 }
 ::= { sipConfiguration 55 }

sipCfgEmergencyServiceURN OBJECT-TYPE
 SYNTAX DisplayString
 MAX-ACCESS read-write
 STATUS current
 DESCRIPTION
  "This is the string that will specify the emergency service urn according to RFC5031"
 ::= { sipConfiguration 56 }

sipCfgSubsAlertTimeout OBJECT-TYPE
 SYNTAX Unsigned32
 MAX-ACCESS read-write
 STATUS current
 DESCRIPTION
  "This MIB Object specifies the alert timeout (time before subscription expiry) in seconds for subscriptions to
   refresh. This MIB can only be applied via the Config File."
 DEFVAL { 60 }
 ::= { sipConfiguration 57 }

 sipCfgProvisionalTimer OBJECT-TYPE
 SYNTAX Unsigned32
 MAX-ACCESS read-write
 STATUS current
 DESCRIPTION
  "This integer specifies the wait time in seconds for final response (Corresponding to Timer C of proxy in RFC 3261).
   The timer is set when receiving a provisional response on an INVITE transaction. If value 0 is set, The INVITE
   transaction will wait forever for the final response.
   This MIB can only be applied via configuration file, and should be used in PC2.0 firmware only."
 ::= { sipConfiguration 58 }

sipCfg3WCWaitHookHoldTimer OBJECT-TYPE
 SYNTAX Unsigned32
 MAX-ACCESS read-write
 STATUS current
 DESCRIPTION
  "This MIB Object specifies the WaitHook Hold Timer in seconds when the Three Way Calling attempt fails
  due to error or busy.Setting it to 0 means no timeout."
 DEFVAL { 0 }
 ::= { sipConfiguration 59 }

 sipCfgWaitHookHoldTone OBJECT-TYPE
 SYNTAX DisplayString
 MAX-ACCESS read-write
 STATUS current
 DESCRIPTION
  "This string specifies the tone used in the two scenarios:
  1. BYE is received from the third party before the Three Way Calling is connected.
  2. BYE is recieved from the talking party when it is in Call Waiting state.
  The tone uses the URI format file:///PacketCableRST/<tone-identifier> or
  http://127.0.0.1/<tone-identifier>
  For example:file:///PacketCableRST/ro or http://127.0.0.1/ro"
  ::= { sipConfiguration 60 }

sipCfgMinSE OBJECT-TYPE
 SYNTAX Integer32
 MAX-ACCESS read-write
 STATUS current
 DESCRIPTION
  "This integer specifies the preferred minimum session expiry(Min-SE) value (in seconds) sent in the INVITE message.
   This value defaults to 90 and the minimum value is 0."
 ::= { sipConfiguration 61 }

 sipCfgInDialogRefer OBJECT-TYPE
 SYNTAX TruthValue
 MAX-ACCESS read-write
 STATUS current
 DESCRIPTION
  "When this MIB value is true(1), it will force the REFER sent within existing dialog from Transferor to Transferee, no
   matter whether the Transferee supports Target-Dialog header or not.
   When the value is false(2), only if the transferee does not support the Target-Dialog header, the transferor will
   initiate call transfer via a REFER sent within the existing dialog with the transferee, otherwise, it will send the REFER
   out of the existing dialog."
 DEFVAL { false }
 ::= { sipConfiguration 62 }

sipCfgFailoverSwitch OBJECT-TYPE
  SYNTAX BITS {
      invite(0),
      cancel(1),
      bye(2),
      update(3),
      publish(4),
      refer(5),
      notify(6),
      subscribe(7),
      unused8(8),
      unused9(9),
      unused10(10),
      unused11(11),
      unused12(12),
      unused13(13),
      unused14(14),
      unused15(15),
      unused16(16),
      unused17(17),
      unused18(18),
      unused19(19),
      unused20(20),
      unused21(21),
      unused22(22),
      unused23(23),
      unused24(24),
      unused25(25),
      unused26(26),
      unused27(27),
      unused28(28),
      unused29(29),
      unused30(30),
      unused31(31)
  }
  MAX-ACCESS read-write
  STATUS current
  DESCRIPTION
    "This object is used to enable failover of SIP non-REGISTER request message. From
     left to right, the specified bit indicates whether or not the failover of
     corresponding message is enabled/disabled when message timeout happens.  For
     example, if the first bit is set, then failover will be triggered when INVITE
     request timeout happens. NO bits are set by default.

     /** BIT Descriptions **/
     0x80000000 : invite
     0x40000000 : cancel
     0x20000000 : bye
     0x10000000 : update
     0x08000000 : publish
     0x04000000 : refer
     0x02000000 : notify
     0x01000000 : subscribe
     "
  DEFVAL { '00000000'h }
 ::= { sipConfiguration 63 }

 sipCfgSubsRetryTimeout OBJECT-TYPE
 SYNTAX Unsigned32
 MAX-ACCESS read-write
 STATUS current
 DESCRIPTION
  "This MIB Object specifies the timer interval in seconds between retry of initial/refresh subscriptions.
   Setting the value to 0 means no retry of initial/refresh subscription."
 DEFVAL { 600 }
 ::= { sipConfiguration 64 }

 sipCfgPAccessNetworkInfoHeaderValue OBJECT-TYPE
 SYNTAX OCTET STRING (SIZE (0..32))
 MAX-ACCESS read-write
 STATUS current
 DESCRIPTION
  "This MIB Object specifies the value that outgoing message would carry in P-Access-Network-Info header.
   DOCSIS is the default value."
 DEFVAL { "DOCSIS" }
 ::= { sipConfiguration 65 }

 sipCfgTermOffHookProcessingDelay OBJECT-TYPE
 SYNTAX Unsigned32 (0..60)
 MAX-ACCESS read-write
 STATUS current
 DESCRIPTION
  "This MIB object specifies the delay time in seconds after a call is terminated before Extended Off Hook Processing begins, if the device remains off-hook."
 DEFVAL { 20 }
 ::= { sipConfiguration 66 }

 sipCfgT2 OBJECT-TYPE
 SYNTAX Integer32
 MAX-ACCESS read-write
 STATUS current
 DESCRIPTION
  "This integer specifies the maximum retransmit interval for non-INVITE requests and INVITE responses (T2 in RFC 3261) in milliseconds. It is recommended to set the timer equal or larger than 4000 milliseconds."
 ::= { sipConfiguration 67 }

 sipCfgRegInterval OBJECT-TYPE
 SYNTAX Integer32
 MAX-ACCESS read-write
 STATUS current
 DESCRIPTION
  "This MIB object specifies the intervals between registrations of each line when system boots up. It means each lines register separately if the value of sipCfgRegInterval MIB is 0"
 DEFVAL { 0 }
 ::= { sipConfiguration 68 }

 sipCfgOnhookDelayTimer OBJECT-TYPE
 SYNTAX Integer32
 MAX-ACCESS read-write
 STATUS current
 DESCRIPTION
  "This MIB object specifies the delay time of terminating the call when onhook. If the value is 0 which means the feature is disabled"
 DEFVAL { 0 }
 ::= { sipConfiguration 69 }

 sipCfgNetConfFactoryUri OBJECT-TYPE
 SYNTAX DisplayString
 MAX-ACCESS read-write
 STATUS current
 DESCRIPTION
  "This MIB object specifies the conference factory URI.
   If configured, on the second flash of a three-way call, EMTA will generate an INVITE to this URI for network conference creation.
   If not configured, the conference call will be placed locally."
 ::= { sipConfiguration 70 }

 sipCfgSipFeatureSwitch3 OBJECT-TYPE
  SYNTAX BITS {
      publishTimestampsDST(0),
      playRtpForSecond183WithoutSdp(1),
      addSipInstanceToContact(2),
      notPopulateFirstPAURIFrom200OK(3),
      judgeSDPWhileReturnFalse(4),
      tcpFailTryUDP(5),
      reuseTCPConnection(6),
      sdpEndsWithEmptyLine0x0d0a(7),
      doNotRedirect3xxResponseForInvite(8),
      pcscfWhiteList(9),
      processUnsolicitedNotifyForRegEvent(10),
      prependZerosToCIDDisplayNumber(11),
      terminateConnBeforeInForkCallFlow(12),
      teardownCallOn403503(13),
      alwaysRegWhenGoingOffhook(14),
      allowDialingWithoutReg(15),
      usePEarlyMediaHeader(16),
      useFromInsteadOfPAssertedID(17),
      unused18(18),
      unused19(19),
      holdEarlyMediaUntilQosComplete(20),
      suppressDisplayName(21),
      unused22(22),
      unused23(23),
      unused24(24),
      unused25(25),
      unused26(26),
      unused27(27),
      unused28(28),
      unused29(29),
      unused30(30),
      unused31(31)
  }
  MAX-ACCESS read-write
  STATUS current
  DESCRIPTION
    "This object is like sipCfgSipFeatureSwitch. It is used to enable features of
     the Arris SIP MTA. From left to right, the specified bit indicates whether
     or not the corresponding feature is enabled/disabled.  For example, if the
     first bit is set, then the PublishTimestampsDST feature is enabled. If it is zero,
     the feature is disabled.  NO bits are set by default.

     /** BIT Descriptions **/
     0x80000000 : publishTimestampsDST       - With this bit set, the Timestamps in PUBLISH will be transfered to DST.
     0x40000000 : playRtpForSecond183WithoutSdp       - With this bit set, the RTP can continue to play on receiving second 183 without SDP.
     0x20000000 : addSipInstanceToContact    - With this bit set, add the sipInstance(based on RFC 5626) to Contact header in REGISTER and INVITE.
     0x10000000 : notPopulateFirstPAURIFrom200OK  - With this bit set, don't populate IMPUID with the first P-Associated-URI header from 200 OK to REGISTER.
     0x08000000 : judgeSDPWhileReturnFalse - With this bit set, judge SDP with o= while SDPChange return FALSE.
     0x04000000 : tcpFailTryUDP - With this bit set,when a TCP sip message fails,sip message should be send in UDP.
     0x02000000 : reuseTCPConnection - With this bit set, SIP MTA will reuse TCP connection.
     0x01000000 : sdpEndsWithEmptyLine0x0d0a       - With this bit set, add an empty line to the end of SDP of INVITE.
     0x00800000 : doNotRedirect3xxResponseForInvite       - With this bit set, 3xx response to an INVITE will not be redirected. Instead an ACK will be sent after ceasing retransmission of the INVITE.
     0x00400000 : pcscfWhiteList - With this bit set, P-CSCF White list will be enabled.
     0x00200000 : processUnsolicitedNotifyForRegEvent - With this bit set, MTA will process unsolicited NOTIFY for reg event when we do not have an active subscription.
     0x00100000 : prependZerosToCIDDisplayNumber - Prepend 0 to CID Display Number for national dialing or 00 for international dialing
     0x00080000 : terminateConnBeforeInForkCallFlow - With this bit set, terminate the connection before in Fork Call flow instead of disconnecting.
     0x00040000 : teardownCallOn403503 - tear down existing call when receive 403/503 against a re-INVITE message or a BYE message which caused by exssion timer expires
     0x00020000 : alwaysRegWhenGoingOffhook - Always register when user goes offhook if not already registered or actively registering.
     0x00010000 : allowDialingWithoutReg - Apply dialtone and allow outgoing calls without successful SIP Registration (PC2.0 only).
     0x00008000 : usePEarlyMediaHeader - Use the P-Early-Media header, if present, in 18X message to decide whether or not to play ringback tone locally (PC2.0 only).
     0x00004000 : useFromInsteadOfPAssertedID - Use the From header for the Caller-ID Display values instead of the P-Asserted-Identity header.
     0x00002000 : unused
     0x00001000 : unused
     0x00000800 : holdEarlyMediaUntilQosComplete - Delay start of early media RTP until QoS completes
     0x00000400 : suppressDisplayName - With this bit set, there will be no display name in the FROM/P-Preferred-Identity header for outgoing calls.
     0x00000200 : unused
     0x00000100 : unused
     0x00000080 : unused
     0x00000040 : unused
     0x00000020 : unused
     0x00000010 : unused
     0x00000008 : unused
     0x00000004 : unused
     0x00000002 : unused
     0x00000001 : unused
     "
  DEFVAL { '00000000'h }
 ::= { sipConfiguration 71 }

 sipCfgRegisterOnExpire OBJECT-TYPE
     SYNTAX  INTEGER {
             disabled(0),
             enabled(1)
     }

 MAX-ACCESS read-write
 STATUS current
 DESCRIPTION
  "A new MIB sipCfgRegisterOnExpire  is introduced to reset MTA When certain  SIP message is received in order to initialize a new REGISTER message.
If this MIB is enabled, When Subscription is terminated by NOTIFY for reg event which has content state=terminated and event=expired in the body, it will trigger MTA reset process. MTA will not reset until all the lines are idle.
"
 DEFVAL { disabled }
 ::= { sipConfiguration 72 }

 sipCfgServiceCapabilities OBJECT-TYPE
  SYNTAX DisplayString
  MAX-ACCESS read-write
  STATUS current
  DESCRIPTION
   "This MIB object specifies User Agent Capabilities in the Session Initiation Protocol (SIP)(RFC 3840).
    The string specifies User Agent Capabilities, the description of capability separated by semi-colon ';'.
    For example: audio=true;duplex=full;mobility=fixed;description=<phone> ."
  ::= { sipConfiguration 73 }



 sipCfgCIDDisDSTInfo OBJECT-TYPE
  SYNTAX      SnmpAdminString
  MAX-ACCESS  read-write
  STATUS      current
  DESCRIPTION
   " The time zone option including DST information in the 'TZ-Posix String' format as defined in RFC 4833.
     If this attribute is not the zero-length string the UE MUST perform the time correction during the daylight saving time
     per this value and ignore the value of pktcEUERSTCIDDisDSTFlag and pktcEUERSTCIDDisTimeAdj

     If not configured, this attribute takes the value of the timezone acquired by the host system the UE resides or
     defaults to the zero-length string. For example, an EUE reports the value of the TZ-Posix string provided in RFC 4833
     DHCPv4 option 'TZ-POSIX String' or DHCPv6 option code OPTION_NEW_POSIX_TIMEZONE from the CM.

     The following clarifications apply to the 'TZ-Posix String' expression:
     Given the TZ-Posix String as : stdoffset[dst[offset][,start[/time],end[/time]]]

     The EUE may ignore the time zone abbreviation associated with the 'std' and 'dst' expressions or may use them as part of a
     particular time output formatting (e.g., display time with timezone local abbreviation).
     The EUE is not required to support the parsing of the 'start' and 'end' expressions in Julian and zero-based Julian day.
     The EUE MUST apply the default values to the optional components in the TZ-Posiz String."
    ::= { sipConfiguration 74 }

 sipCfgProtectedDnList OBJECT-TYPE
  SYNTAX DisplayString
  MAX-ACCESS read-write
  STATUS current
  DESCRIPTION
   "This MIB is used to configure the list of protected dialed numbers that are not recorded when called.
    Numbers are entered as strings separated by comma ',' and no white space between them,  for example '7705559021,7705559022'."
  ::= { sipConfiguration 75 }

 sipCfgUnsetDontFragmentBit OBJECT-TYPE
 SYNTAX TruthValue
  MAX-ACCESS read-write
  STATUS current
  DESCRIPTION
   "This MIB is used to clear or set don't fragment bit in IP header of SIP packets.
    If the MIB is set to TRUE, don't fragment bit will be 0. If the MIB is set to FALSE, don't fragment bit will be 1.
    Its default value is FALSE."
  DEFVAL { false }
  ::= { sipConfiguration 76 }


  sipCfgMWISubscriptionCheckInterval OBJECT-TYPE
  SYNTAX Integer32
  MAX-ACCESS read-write
  STATUS current
  DESCRIPTION
   "This MIB specifies the interval (in minutes) that MTA checks the MWI subscription state.
    If the line operational status is up and MWI subscription state is unsubscribed it will restart the subscription.
    The default value is 0."
  ::= { sipConfiguration 77 }

 sipCfgHomeAlarmSupport OBJECT-TYPE
  SYNTAX TruthValue
  MAX-ACCESS read-write
  STATUS current
  DESCRIPTION
          "The setting of this MIB enables the MTA to support the Legacy Home Alarm integration."
  DEFVAL { true }
  ::= { sipConfiguration 78 }
  sipCfgUnsolicitedNotifyAcceptSwitch OBJECT-TYPE
  SYNTAX BITS {
      reg(0),
      uaProfile(1),
      messageSummary(2),
      unused3(3),
      unused4(4),
      unused5(5),
      unused6(6),
      unused7(7),
      unused8(8),
      unused9(9),
      unused10(10),
      unused11(11),
      unused12(12),
      unused13(13),
      unused14(14),
      unused15(15),
      unused16(16),
      unused17(17),
      unused18(18),
      unused19(19),
      unused20(20),
      unused21(21),
      unused22(22),
      unused23(23),
      unused24(24),
      unused25(25),
      unused26(26),
      unused27(27),
      unused28(28),
      unused29(29),
      unused30(30),
      unused31(31)
  }
  MAX-ACCESS read-write
  STATUS current
  DESCRIPTION
    "This object is used to enable accepting the unsolicited NOTIFY. From
     left to right, the specified bit indicates whether or not accept the unsolicited NOTIFY for
     the event.  For example, if the first bit is set, unsolicited reg NOTIFY will be accepted.
     /** BIT Descriptions **/
     0x80000000 : reg
     0x40000000 : uaProfile
     0x20000000 : messageSummary
     "
  DEFVAL { '40000000'h }
 ::= { sipConfiguration 79 }

 sipCfgFailbackTimeMin OBJECT-TYPE
 SYNTAX Integer32
 MAX-ACCESS read-create
 STATUS current
 DESCRIPTION
 "This MIB object specifies the start range for SIP fail back timer."
 DEFVAL { 7200 }
 ::= { sipConfiguration 80 }

 sipCfgFailbackTimeMax OBJECT-TYPE
 SYNTAX Integer32
 MAX-ACCESS read-create
 STATUS current
 DESCRIPTION
 "This MIB object specifies the end range for SIP fail back timer."
 DEFVAL { 21600 }
 ::= { sipConfiguration 81 }


arrisSipIPv6Mib OBJECT IDENTIFIER ::= {arrisSipMib 4}

arrisSipIPv6MaxUDPSize OBJECT-TYPE
 SYNTAX Integer32
 MAX-ACCESS read-write
 STATUS current
 DESCRIPTION
  "This integer specifies the threshold at which point packets will begin being sent over TCP rather than UDP for IPv6 only.
   When set to zero, no threshold exists and all packets will be sent using UDP. It is for IPv6 SIP request messages only."
 DEFVAL { 1280 }
 ::= { arrisSipIPv6Mib 1 }


arrisSipIPv6IpPreferenceOverride OBJECT-TYPE
      SYNTAX      INTEGER {dhcp(0), ipv4(1), ipv6(2),
                           ipv4SecIpv6(3), ipv6SecIpv4(4), ipv6BypassDssid(5) }
	    MAX-ACCESS  read-write
      STATUS      current
      DESCRIPTION "The value of this MIB overrides the eUE IP addressing mode preference specified via the eCM DHCP exchange.
      If this MIB is set to any value other than 0(dhcp), the eUE will choose its preference based on the MIB setting
      as opposed to any preference that is specified by the DHCP exchange.
      The values are as follows:
         dhcp(0) - No override, eUE uses preference per eCM DHCP exchange
         ipv4(1) - eUE operates in single-stack IPv4 addressing mode
         ipv6(2) - eUE operates in single-stack IPv6 addressing mode
         ipv4SecIpv6(3) - eUE acquires IPv4 primary address, IPv6 secondary address
         ipv6SecIpv4(4) - eUE acquires IPv6 primary address, IPv4 secondary address
         ipv6BypassDssid(5) - eUE operates in single-stack IPv6 addressing mode, bypass the DSS_ID check
      Default is dhcp, except for CT loads, where option is ipv4."
      ::= { arrisSipIPv6Mib 2 }
END
