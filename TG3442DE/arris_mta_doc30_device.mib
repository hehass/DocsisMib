ARRIS-MTA-DOC30-DEVICE-MIB DEFINITIONS ::= BEGIN

IMPORTS
   MODULE-IDENTITY,
   OBJECT-TYPE,
   Integer32,
   Counter32,
   Counter64,
   IpAddress
      FROM SNMPv2-SMI
   arrisProdIdCM
      FROM ARRIS-MIB
   TruthValue, DisplayString, TimeStamp, DateAndTime, TEXTUAL-CONVENTION
      FROM SNMPv2-TC
   SnmpAdminString
      FROM SNMP-FRAMEWORK-MIB;

arrisMtaDoc30Mib MODULE-IDENTITY
     LAST-UPDATED    "1010200000Z"  -- October 20, 2010
     ORGANIZATION    "ARRIS Broadband"
     CONTACT-INFO    "Chris Hare
                      Postal: ARRIS Broadband
                      3871 Lakefield Drive
                      Suite 300
                      Suwanee, GA 30024-1242
                      U.S.A.
                      Phone:  +1 770-473-5165
                      E-mail: chris.hare@arrisi.com"
     DESCRIPTION
         "This MIB module supplies the basic proprietary
          management objects for ARRIS MTA devices on DOCSIS 3.0 modems."


-- Revision history
    REVISION    "1010200000Z"  -- October 20, 2010
    DESCRIPTION
        "Initial version"
    ::= { arrisProdIdCM 5 }



-- This MIB module contains the following groups.
arrisMtaDoc30MibObjects            OBJECT IDENTIFIER ::= { arrisMtaDoc30Mib 1 }

arrisMtaDoc30Base                  OBJECT IDENTIFIER ::= { arrisMtaDoc30MibObjects 1 }
arrisMtaDoc30Setup                 OBJECT IDENTIFIER ::= { arrisMtaDoc30MibObjects 2 }

arrisMtaDoc30EmergencyNumber       OBJECT-TYPE
 SYNTAX DisplayString (SIZE (0..50))
 MAX-ACCESS read-write
 STATUS current
 DESCRIPTION
  "This is the string that will specify the emergency number.  A call to the emergency number will modify the the QoS priority to the highest level."
 ::= { arrisMtaDoc30Setup 1 }

arrisMtaDoc30RootCertType       OBJECT-TYPE
 SYNTAX INTEGER{ testRoot(1), realRoot(2) }
 MAX-ACCESS read-write
 STATUS current
 DESCRIPTION
  "This object indicates the iptel root certificate type currently being used
  for MTA security.  It also provides the ability to change, only at provisioning,
  the iptel root certificate type to use for MTA security.  This MIB should
  only be set from the CM configuration file."
 ::= { arrisMtaDoc30Setup 2 }

arrisMtaDoc30AdjustCallpFeatureSwitch OBJECT-TYPE
    SYNTAX INTEGER {
        disable(0),
        enable(1)
    }
    MAX-ACCESS read-write
    STATUS current
    DESCRIPTION
        "This MIB object is used to adjust some bits of the ppCfgMtaCallpFeatureSwitch to a value that will allow the same operation as in the TS6.x FW releases. The default value is disable(0)."
    ::= { arrisMtaDoc30Setup 3 }

arrisMtaDoc30InvalidateTickets   OBJECT-TYPE
    SYNTAX INTEGER{
       enable(1),
       disable(0)
    }
    MAX-ACCESS read-write
    STATUS current
    DESCRIPTION
       "This MIB object instructs an MTA to invalidate (and flush from NVRAM) all Provisioning
       and CMS server Kerberos Tickets when MTA provisioning has stopped and the provisioning timer has expired.
       The object value is encoded as follows:
       enable (1) means that the MTA MUST immediately invalidate the Kerberos Application Ticket for the Provisioning
       Application and all CMS Application Tickets
       disable(0) means that the MTA will use the Provisioning and CMS Application Tickets currently stored in NVRAM
       The default value is disable(0)."
    DEFVAL {disable}
    ::= { arrisMtaDoc30Setup 4 }


END
