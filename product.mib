TI-PRODUCTION-MIB DEFINITIONS ::= BEGIN

IMPORTS
        MacAddress,
        DateAndTime,
        DisplayString,
        TruthValue
            FROM SNMPv2-TC
        MODULE-IDENTITY,
        OBJECT-TYPE,
        Integer32,
        Unsigned32,
        IpAddress
            FROM SNMPv2-SMI
        eqName
            FROM TI-MANUFACTURER-MIB
        DocsisUpstreamType
            FROM DOCS-IF-MIB;

modemProduction MODULE-IDENTITY
        LAST-UPDATED    "200805040000Z"
        ORGANIZATION    "TEXAS INSTRUMENTS"
        CONTACT-INFO
                "Igor Stadnik
                Postal: TEXAS INSTRUMENTS
                Hasadnaot 8, Herzlia 46766,
                Israel. "

        DESCRIPTION
            " This is the private MIB module for the Puma5 Cable Modem Production"
        ::= { eqName 2 }

-- This MIB module contains the following groups.
modemProdCmSetup               OBJECT IDENTIFIER ::= { modemProduction 1}
modemProdCmTest                OBJECT IDENTIFIER ::= { modemProduction 2}
-- Production groups
modemProdCmPermanentSetup      OBJECT IDENTIFIER ::= { modemProdCmSetup 1}
modemProdCmManufacturingSetup  OBJECT IDENTIFIER ::= { modemProdCmSetup 2}
modemProdCmCalibrationSetup    OBJECT IDENTIFIER ::= { modemProdCmSetup 3}
modemProdDownstreamCalibration OBJECT IDENTIFIER ::= { modemProdCmCalibrationSetup 1}
modemProdUpstreamTransmit      OBJECT IDENTIFIER ::= { modemProdCmCalibrationSetup 2}
modemProdUpstreamCalibration   OBJECT IDENTIFIER ::= { modemProdCmCalibrationSetup 3}


-- The access to all MIB objects is self-controlled by modemProdMibAccessControl
-- persistent object. It means that all MIB objects may be accessed in three
-- different access modes: maxaccess, limitedaccess and nonaccessible.
-- In nonaccessible mode the MIB will be unvisible. Objects are grouped to
-- support different behavior in limitedaccess mode. The group access may be
-- controlled by SNMP view.
--
--                                        maxaccess  limited
-- modemProdCmPermanentSetup --------------------------------------
--       modemProdCmCertServerIp              RW      not-accessible
--       modemProdCmCertFileName              RW      not-accessible
--       modemProdCmCertKeyFileName           RW      not-accessible
--       modemProdCmCertFrequencyPlan         RW      not-accessible
--       modemProdCmCertDownload              RW      not-accessible
--       modemProdCmCertOperStat              R       not-accessible


-- modemProdCmManufacturingSetup ----------------------------------
--       modemProdMibAccessControl            RW      R
--       modemProdSerialNumber                R       R
--       modemProdMtaEnable                   RW      R
--       modemProdMfgOrganizationName         RW      R
--       modemProdCvcAccessStart              RW      R
--       modemProdCodeAccessStart             RW      R
--       modemProdLanIp                       RW      R
--       modemProdHostIp                      RW      R
--       modemProdIpMask                      RW      R
--       modemProdInterfaceName               RW      R
--       modemProdCmMacAddress                RW      R
--       modemProdLanMacAddress               RW      R
--       modemProdUsbDevMacAddress            RW      R
--       modemProdUsbHostMacAddress           RW      R
--       modemProdBaudRate                    RW      R
--       modemProdTunersNumber                RW      R
--       modemProdDocsisPhyMultFact           RW      R
--       modemProdTunerType                   RW      R
--       modemProdPgaType                     RW      R
--       modemProdHwRevision                  RW      R
--       modemProdFrequencyPlan               RW      R

-- modemProdCmCalibrationSetup ----------------------------------
--   modemProdDownstreamCalibration
--     modemProdDsCalibrationOperStatus       R       not-accessible
--     modemProdDsCalibrationAdminStatus      RW      not-accessible

--     modemProdPowerCalibrationTable  ------------------------------
--       modemProdDsCallIndex                   not-accessible
--       modemProdDsFrequency                 RW      not-accessible
--       modemProdDsPower                     RW      not-accessible

--   modemProdUpstreamTransmit ----------------------------------
--     modemProdUpTransGain                   RW      not-accessible

--     modemProdUpstreamTransmitTable ----------------------------------
--     modemProdUsTransmitlIndex                not-accessible
--     modemProdUsFrequency                   RW      not-accessible
--     modemProdUsModulation                  RW      not-accessible
--     modemProdUsSymbolRate                  RW      not-accessible
--     modemProdUsAttenuation                 RW      not-accessible
--     modemProdUsTransmitionType             RW      not-accessible
--     modemProdUsBurst                       RW      not-accessible

--   modemProdUpstreamCalibration ----------------------------------
--     modemProdUsCalibrationTableErase       RW      not-accessible
--     modemProdUsCalibrationModeFactor       RW      not-accessible
--     modemProdUsCalibrationPowerDelta       RW      not-accessible

--     modemProdUpstreamCalibrationTable ----------------------------------
--       modemProdUsCalibrationIndex            not-accessible
--       modemProdUsCalibrationPower          R       not-accessible

--     modemProdFrequencyCalibrationTable ----------------------------------
--       modemProdUsFreqCalibrationIndex        not-accessible
--       modemProdUsFreqCalibrationPower      RW      not-accessible

--     modemProdPgaAttenuationTable ----------------------------------
--       modemProdUsPgaAttenIndex               not-accessible
--       modemProdUsPgaAttenPower             RW      not-accessible

--     modemProdCurrentModeFactorTable ----------------------------------
--       modemProdUsCmfIndex                    not-accessible
--       modemProdUsCmfPower                  RW      not-accessible

--     modemProdUsCalibrationUpdateFlash      RW      not-accessible





-- modemProdCmPermanentSetup ----------------------------------------------

modemProdCmCertServerIp   OBJECT-TYPE
        SYNTAX         IpAddress
        MAX-ACCESS     read-write
        STATUS         current
        DESCRIPTION
            "This object shows and sets the certificate download server IP Address."
        ::= { modemProdCmPermanentSetup 1 }

modemProdCmCertFileName   OBJECT-TYPE
        SYNTAX         DisplayString (SIZE (0..80))
        MAX-ACCESS     read-write
        STATUS         current
        DESCRIPTION
            "This object shows and sets the certificate filename."
        ::= { modemProdCmPermanentSetup 2 }

modemProdCmCertKeyFileName OBJECT-TYPE
        SYNTAX         DisplayString (SIZE (0..80))
        MAX-ACCESS     read-write
        STATUS         current
        DESCRIPTION
            "This object shows and sets the certificate key filename."
        ::= { modemProdCmPermanentSetup 3 }

modemProdCmCertFrequencyPlan OBJECT-TYPE
        SYNTAX  INTEGER {
            unknown(0),
            northAmerican(1),
            european(2),
            japanese(3)
        }
        MAX-ACCESS     read-write
        STATUS         current
        DESCRIPTION
            "This object shows and sets the certificate frequency plan."
        ::= { modemProdCmPermanentSetup 4 }

modemProdCmCertDownload OBJECT-TYPE
        SYNTAX         TruthValue
        MAX-ACCESS     read-write
        STATUS         current
        DESCRIPTION
            "Initiates a certificate download for the selected bank.
            All previously certificate download parameters must be predefined.
            Always returns False(2), which does nothing."
        ::= { modemProdCmPermanentSetup 5 }

modemProdCmCertOperStat OBJECT-TYPE
        SYNTAX  INTEGER {
            unknown(0),
            downloadInProgress(1),
            downloadSuccess(2),
            downloadFailed(3)
        }
        MAX-ACCESS     read-only
        STATUS         current
        DESCRIPTION
            "This object shows the SW operational process status."
        ::= { modemProdCmPermanentSetup 6 }



-- modemProdCmManufacturingSetup ----------------------------------------------

modemProdMibAccessControl  OBJECT-TYPE
        SYNTAX  INTEGER {
            maxaccess(1),
            limitedaccess(2),
            nonaccessible(3)
        }
        MAX-ACCESS  read-write
        STATUS      current
        DESCRIPTION
            "This object controls the SNMP access level for modemProduction Mibs.
            The value of this object is stored into the NVRAM."
        ::= { modemProdCmManufacturingSetup 1}

modemProdSerialNumber  OBJECT-TYPE
        SYNTAX  DisplayString (SIZE (1..10))
        MAX-ACCESS  read-only
        STATUS  current
        DESCRIPTION
            "This object shows the Serial Number.
            The Serial Number is retrieved from serialDate and modemProdCmMacAddress.
            MYXXXXXXXX when:
            M: month = Jan(1), Feb(2), Mar(3), Apl(4), May(5), Jun(6),
            Jul(7), Aug(8), Sep(9), Oct(X), Nov(Y), Dec(Z).
            Y: year = 2001(1), 2002(2), 2009(9).
            XXXXXXXX: Eight-digit decimal value of the last three bytes
            of the CM MAC address.
            The value of this object is stored into the NVRAM."
        ::= { modemProdCmManufacturingSetup 2 }

modemProdMtaEnable OBJECT-TYPE
        SYNTAX         TruthValue
        MAX-ACCESS     read-write
        STATUS         current
        DESCRIPTION
            "This object is used to enable MTA feature flag.
            Set to true(1) to enable MTA flag.
            Set to false(2) to disable MTA flag.
            The value of this object is stored in the NVRAM."
        ::= { modemProdCmManufacturingSetup 3 }

modemProdMfgOrganizationName  OBJECT-TYPE
        SYNTAX  DisplayString
        MAX-ACCESS  read-write
        STATUS  current
        DESCRIPTION
            "Shows the sets CM's MFG Organization Name.
            The value of this object is stored in the NVRAM."
        ::= { modemProdCmManufacturingSetup 4 }

modemProdCvcAccessStart OBJECT-TYPE
        SYNTAX  DateAndTime
        MAX-ACCESS  read-write
        STATUS  current
        DESCRIPTION
            "This object shows the CVC Access Start Time into the CM.
            The value of this object is stored into the NVRAM."
        ::= { modemProdCmManufacturingSetup 5 }

modemProdCodeAccessStart OBJECT-TYPE
        SYNTAX  DateAndTime
        MAX-ACCESS  read-write
        STATUS  current
        DESCRIPTION
            "This object shows the Code Access Start Time into the CM.
            The value of this object is stored into the NVRAM."
        ::= { modemProdCmManufacturingSetup 6 }

modemProdLanIp OBJECT-TYPE
        SYNTAX  IpAddress
        MAX-ACCESS  read-write
        STATUS  current
        DESCRIPTION
            "Shows and sets the LAN IP Address.
            The value of this object is stored into the NVRAM."
        ::= { modemProdCmManufacturingSetup 7 }

modemProdHostIp OBJECT-TYPE
        SYNTAX  IpAddress
        MAX-ACCESS  read-write
        STATUS  current
        DESCRIPTION
            "Shows and sets the Host IP Address.
            The value of this object is stored into the NVRAM."
        ::= { modemProdCmManufacturingSetup 8 }

modemProdIpMask OBJECT-TYPE
        SYNTAX  IpAddress
        MAX-ACCESS  read-write
        STATUS  current
        DESCRIPTION
            "Shows and sets the Host IP Mask.
            The value of this object is stored into the NVRAM."
        ::= { modemProdCmManufacturingSetup 9 }

modemProdInterfaceName OBJECT-TYPE
        SYNTAX  DisplayString
        MAX-ACCESS  read-write
        STATUS  current
        DESCRIPTION
            "Shows and sets interface Name.
            The value of this object is stored into the NVRAM."
        ::= { modemProdCmManufacturingSetup 10 }

modemProdCmMacAddress OBJECT-TYPE
        SYNTAX  MacAddress
        MAX-ACCESS  read-write
        STATUS  current
        DESCRIPTION
            "This object shows the 48-bit Cable Modem MAC address.
            The value of this object is stored into the NVRAM."
        ::= { modemProdCmManufacturingSetup 11 }

modemProdLanMacAddress OBJECT-TYPE
        SYNTAX  MacAddress
        MAX-ACCESS  read-write
        STATUS  current
        DESCRIPTION
            "This object shows the 48-bit Lan MAC address.
            The value of this object is stored into the NVRAM."
        ::= { modemProdCmManufacturingSetup 12 }

modemProdUsbDevMacAddress OBJECT-TYPE
        SYNTAX  MacAddress
        MAX-ACCESS  read-write
        STATUS  current
        DESCRIPTION
            "This object shows the 48-bit USB device MAC address.
            The value of this object is stored into the NVRAM."
        ::= { modemProdCmManufacturingSetup 13 }

modemProdUsbHostMacAddress OBJECT-TYPE
        SYNTAX  MacAddress
        MAX-ACCESS  read-write
        STATUS  current
        DESCRIPTION
            "This object shows the 48-bit USB host MAC address.
            The value of this object is stored into the NVRAM."
        ::= { modemProdCmManufacturingSetup 14 }

modemProdBaudRate OBJECT-TYPE
        SYNTAX  INTEGER {
            unknown(0),
            br2400(1),
            br4800(2),
            br9600(3),
            br19200(4),
            br38400(5),
            br115200(6)
        }
        MAX-ACCESS  read-write
        STATUS  current
        DESCRIPTION
            "Shows and sets the CM baud rate.
            The value of this object is stored into the NVRAM."
        ::= { modemProdCmManufacturingSetup 15 }

modemProdTunersNumber OBJECT-TYPE
        SYNTAX  INTEGER (1..20)
        MAX-ACCESS  read-write
        STATUS  current
        DESCRIPTION
            "Shows and sets the numbers of tuners.
            The value of this object is stored into the NVRAM."
        ::= { modemProdCmManufacturingSetup 16 }

modemProdDocsisPhyMultFact OBJECT-TYPE
        SYNTAX  INTEGER
        MAX-ACCESS  read-write
        STATUS  current
        DESCRIPTION
            "Shows and sets the DOCSIS Phy Mult Fact.
            The value of this object is stored into the NVRAM."
        ::= { modemProdCmManufacturingSetup 17 }

modemProdTunerType OBJECT-TYPE
        SYNTAX  INTEGER {
            unknown(0),
            mt2060(1),
            mt2064(2),
            mt2068(3),
            mt2170(4),
            anadAt1061(5)
        }
        MAX-ACCESS  read-write
        STATUS  current
        DESCRIPTION
            "Shows and sets the CM tuner type.
            The value of this object is stored into the NVRAM."
        ::= { modemProdCmManufacturingSetup 18 }

modemProdPgaType OBJECT-TYPE
        SYNTAX  INTEGER {
            unknown(0),
            anadAra2017(1)
        }
        MAX-ACCESS  read-write
        STATUS  current
        DESCRIPTION
            "Shows and sets the CM PGA type.
            The value of this object is stored into the NVRAM."
        ::= { modemProdCmManufacturingSetup 19 }

modemProdHwRevision OBJECT-TYPE
        SYNTAX  INTEGER
        MAX-ACCESS  read-write
        STATUS  current
        DESCRIPTION
            "Shows the boot HW major and minor revisions in the form XX.YY, where:
            XX: two-digit decimal value of a major revision.
            YY: two-digit decimal value of a minor revision.
            The value of this object is stored into the NVRAM."
        ::= { modemProdCmManufacturingSetup 20 }

modemProdFrequencyPlan OBJECT-TYPE
        SYNTAX  INTEGER {
            unknown(0),
            northAmerican(1),
            european(2),
            japanese(3),
            hybrid(4)
        }
        MAX-ACCESS  read-write
        STATUS  current
        DESCRIPTION
            "Shows and sets the CM Frequency Plan.
            The value of this object is stored into the NVRAM."
        ::= { modemProdCmManufacturingSetup 21 }

modemProdEnableCli OBJECT-TYPE
        SYNTAX      TruthValue
        MAX-ACCESS  read-write
        STATUS      current
        DESCRIPTION
             "Set the CLI on or off.
              Setting to true(1) turns on CLI.  Setting to false(2) turns
              off CLI. The value is also stored into NV and will be
              operational after next reboot. Returns current setting."
        ::= { modemProdCmManufacturingSetup 22 }




-- modemProdCmCalibrationSetup ----------------------------------

modemProdDsCalibrationOperStatus OBJECT-TYPE
        SYNTAX  INTEGER {
            emptyTable(1),
            completeTable(2),
            callibrationInProgress(3),
            callibrationComplete(4)
        }
        MAX-ACCESS     read-only
        STATUS         current
        DESCRIPTION
            "Displays the status of calibration process. An empty value
            is returned until all of the requested data is filled.
            A ready value indicates that all of the requested data exists
            and the CM is ready to start the calibration process."
        ::= { modemProdDownstreamCalibration 1 }


modemProdDsCalibrationAdminStatus OBJECT-TYPE
        SYNTAX  INTEGER {
            validateAndStart(1),
            validateOnly(2),
            startOnly(3),
            erase(4)
        }
        MAX-ACCESS     read-write
        STATUS         current
        DESCRIPTION
            "Operate the downstream calibration table - validate data,
            start calibration and erase table."
        ::= { modemProdDownstreamCalibration 2 }


--     modemProdPowerCalibrationTable  ------------------------------

   modemProdPowerCalibrationTable OBJECT-TYPE
        SYNTAX              SEQUENCE OF    ModemProdPowerCalibrationEntry
        MAX-ACCESS          not-accessible
        STATUS              current
        DESCRIPTION
            "This object shows the downstream power calibration table.
            The value of this object is stored into the NVRAM."
        ::= { modemProdDownstreamCalibration 3 }

   modemProdPowerCalibrationEntry OBJECT-TYPE
        SYNTAX              ModemProdPowerCalibrationEntry
        MAX-ACCESS          not-accessible
        STATUS              current
        DESCRIPTION
             "Each entry contains objects describing attributes of
        one calibration frequncy and apropriate one calibration power.
        An entry in this table exists for each index of frequency
        and power vectors."
        INDEX               { modemProdDsCallIndex }
        ::= { modemProdPowerCalibrationTable 1 }

   ModemProdPowerCalibrationEntry ::= SEQUENCE {
        modemProdDsCallIndex       INTEGER,
        modemProdDsFrequency       Integer32,
        modemProdDsPower           Integer32
        }

   modemProdDsCallIndex  OBJECT-TYPE
        SYNTAX         INTEGER (1..10)
        MAX-ACCESS     not-accessible
        STATUS         current
        DESCRIPTION
             "The value of this object is index in frequency and power vectors."
        ::= { modemProdPowerCalibrationEntry 1 }

   modemProdDsFrequency  OBJECT-TYPE
        SYNTAX  Integer32 (80000..1300000)
        UNITS   "herz"
        MAX-ACCESS  read-write
        STATUS  current
        DESCRIPTION
            "The value of this object is frequency value into the vector."
        ::= { modemProdPowerCalibrationEntry 2 }

   modemProdDsPower  OBJECT-TYPE
        SYNTAX  Integer32 (-700..700)
        UNITS   "0.01 dbmV"
        MAX-ACCESS  read-write
        STATUS  current
        DESCRIPTION
            "The value of this object is power value into the vector."
        ::= { modemProdPowerCalibrationEntry 3 }



--   modemProdUpstreamTransmit ----------------------------------


   modemProdUpTransGain  OBJECT-TYPE
        SYNTAX         INTEGER
        MAX-ACCESS  read-write
        STATUS         current
        DESCRIPTION
             "Shows and sets Program US PGA gain value.
             The value of this object is stored in the NVRAM."
        ::= { modemProdUpstreamTransmit 1 }


--     modemProdUpstreamTransmitTable ----------------------------------

   modemProdUpstreamTransmitTable OBJECT-TYPE
        SYNTAX              SEQUENCE OF    ModemProdUpstreamTransmitEntry
        MAX-ACCESS          not-accessible
        STATUS              current
        DESCRIPTION
            "This object shows the upstream transmit table.
            The value of this object is stored into the NVRAM."
        ::= { modemProdUpstreamTransmit 2 }

   modemProdUpstreamTransmitEntry OBJECT-TYPE
        SYNTAX              ModemProdUpstreamTransmitEntry
        MAX-ACCESS          not-accessible
        STATUS              current
        DESCRIPTION
             "Each entry contains objects describing attributes for one
        upstream channel.
        An entry in this table exists for each upstream channel."
        INDEX               { modemProdUsTransmitlIndex }
        ::= { modemProdUpstreamTransmitTable 1 }

   ModemProdUpstreamTransmitEntry ::= SEQUENCE {
        modemProdUsTransmitlIndex  INTEGER,
        modemProdUsFrequency       Integer32,
        modemProdUsModulation      INTEGER,
        modemProdUsSymbolRate      INTEGER,
        modemProdUsAttenuation     Integer32,
        modemProdUsTransmitionType INTEGER,
        modemProdUsBurst           INTEGER
        }

   modemProdUsTransmitlIndex  OBJECT-TYPE
        SYNTAX         INTEGER (1..4)
        MAX-ACCESS     not-accessible
        STATUS         current
        DESCRIPTION
             "The value of this object is index represents Us channel."
        ::= { modemProdUpstreamTransmitEntry 1 }

   modemProdUsFrequency  OBJECT-TYPE
        SYNTAX  Integer32
        UNITS   "herz"
        MAX-ACCESS  read-write
        STATUS  current
        DESCRIPTION
            "Set upstream to frequency for selected channel.
            The value of this object is stored in the NVRAM."
        ::= { modemProdUpstreamTransmitEntry 2 }

   modemProdUsModulation  OBJECT-TYPE
        SYNTAX  INTEGER {
            qpsk(1),
            qam8(2),
            qam16(3),
            qam32(4),
            qam64(5),
            qam128(6),
            qam256(7)
        }
        MAX-ACCESS  read-write
        STATUS  current
        DESCRIPTION
            "Set upstream modulation for selected channel.
            The value of this object is stored in the NVRAM."
        ::= { modemProdUpstreamTransmitEntry 3 }

   modemProdUsSymbolRate  OBJECT-TYPE
        SYNTAX  INTEGER {
            sr1(1),
            sr2(2),
            sr4(3),
            sr8(4),
            sr16(5),
            sr32(6)
        }
        MAX-ACCESS  read-write
        STATUS  current
        DESCRIPTION
             "Set symbolRate*160Ksymb for selected channel.
             The value of this object is stored in the NVRAM."
        ::= { modemProdUpstreamTransmitEntry 4 }

   modemProdUsAttenuation  OBJECT-TYPE
        SYNTAX  Integer32
        UNITS   "dB"
        MAX-ACCESS  read-write
        STATUS  current
        DESCRIPTION
            "Set digital gain for selected channel.
            The value of this object is stored in the NVRAM."
        ::= { modemProdUpstreamTransmitEntry 5 }

   modemProdUsTransmitionType  OBJECT-TYPE
        SYNTAX  INTEGER {
            stop(1),
            data(2),
            syn(3)
        }
        MAX-ACCESS  read-write
        STATUS  current
        DESCRIPTION
             "Program US cont for selected channel.
             The value of this object is stored in the NVRAM."
        ::= { modemProdUpstreamTransmitEntry 6 }

   modemProdUsBurst  OBJECT-TYPE
        SYNTAX  INTEGER
        MAX-ACCESS  read-write
        STATUS  current
        DESCRIPTION
            "Transmit US bursts for selected channel.
            The value of this object is stored in the NVRAM."
        ::= { modemProdUpstreamTransmitEntry 7 }



--   modemProdUpstreamCalibration ----------------------------------

   modemProdUsCalibrationTableErase  OBJECT-TYPE
        SYNTAX  INTEGER {
            pgaParams(1),
            cmfParams(2),
            freqParams(3),
            allTables(4)
        }
        MAX-ACCESS  read-write
        STATUS  current
        DESCRIPTION
             "Erase one or all upstream calibration table."
        ::= { modemProdUpstreamCalibration 1 }

   modemProdUsCalibrationModeFactor  OBJECT-TYPE
        SYNTAX         INTEGER (1..7)
        MAX-ACCESS  read-write
        STATUS         current
        DESCRIPTION
             "Set upstream calibration current mode factor.
             The value of this object is stored in the NVRAM."
        ::= { modemProdUpstreamCalibration 2 }

   modemProdUsCalibrationPowerDelta  OBJECT-TYPE
        SYNTAX  Integer32
        UNITS   "dB"
        MAX-ACCESS  read-write
        STATUS  current
        DESCRIPTION
            "Set upstream calibration power delta.
            The value of this object is stored in the NVRAM."
        ::= { modemProdUpstreamCalibration 3 }


--     modemProdUpstreamCalibrationTable ----------------------------------

   modemProdUpstreamCalibrationTable OBJECT-TYPE
        SYNTAX              SEQUENCE OF    ModemProdUpstreamCalibrationEntry
        MAX-ACCESS          not-accessible
        STATUS              current
        DESCRIPTION
            "This object shows the upstream calibration table.
            The value of this object is stored into the NVRAM."
        ::= { modemProdUpstreamCalibration 4 }

   modemProdUpstreamCalibrationEntry OBJECT-TYPE
        SYNTAX              ModemProdUpstreamCalibrationEntry
        MAX-ACCESS          not-accessible
        STATUS              current
        DESCRIPTION
             "Each entry contains objects describing attributes for one
        upstream channel.
        An entry in this table exists for each upstream channel."
        INDEX               { modemProdUsCalibrationIndex }
        ::= { modemProdUpstreamCalibrationTable 1 }

   ModemProdUpstreamCalibrationEntry ::= SEQUENCE {
        modemProdUsCalibrationIndex       INTEGER,
        modemProdUsCalibrationPower       Integer32
        }

   modemProdUsCalibrationIndex  OBJECT-TYPE
        SYNTAX         INTEGER (1..4)
        MAX-ACCESS     not-accessible
        STATUS         current
        DESCRIPTION
             "The value of this object is index represents Us channel."
        ::= { modemProdUpstreamCalibrationEntry 1 }

   modemProdUsCalibrationPower  OBJECT-TYPE
        SYNTAX  Integer32
        UNITS   "dB"
        MAX-ACCESS  read-only
        STATUS  current
        DESCRIPTION
            "Read reported power of selected channel.
            The value of this object is stored in the NVRAM."
        ::= { modemProdUpstreamCalibrationEntry 2 }



--     modemProdFrequencyCalibrationTable ----------------------------------

   modemProdFrequencyCalibrationTable OBJECT-TYPE
        SYNTAX              SEQUENCE OF    ModemProdFrequencyCalibrationEntry
        MAX-ACCESS          not-accessible
        STATUS              current
        DESCRIPTION
            "This object shows the frecuency calibration table.
            The value of this object is stored into the NVRAM."
        ::= { modemProdUpstreamCalibration 5 }

   modemProdFrequencyCalibrationEntry OBJECT-TYPE
        SYNTAX              ModemProdFrequencyCalibrationEntry
        MAX-ACCESS          not-accessible
        STATUS              current
        DESCRIPTION
             "Each entry contains objects describing attributes for Us
        requency vector.
        An entry in this table exists for each frequency."
        INDEX               { modemProdUsFreqCalibrationIndex }
        ::= { modemProdFrequencyCalibrationTable 1 }

   ModemProdFrequencyCalibrationEntry ::= SEQUENCE {
        modemProdUsFreqCalibrationIndex   Integer32,
        modemProdUsFreqCalibrationPower   Integer32
        }

   modemProdUsFreqCalibrationIndex  OBJECT-TYPE
        SYNTAX         Integer32
        UNITS          "herz"
        MAX-ACCESS     not-accessible
        STATUS         current
        DESCRIPTION
            "The value of this object is index represents Us frequency.
            The value of this object is stored in the NVRAM."
        ::= { modemProdFrequencyCalibrationEntry 1 }

   modemProdUsFreqCalibrationPower  OBJECT-TYPE
        SYNTAX  Integer32
        UNITS   "dBmV"
        MAX-ACCESS  read-only
        STATUS  current
        DESCRIPTION
            "Set power for frequency calibration value.
            The value of this object is stored in the NVRAM."
        ::= { modemProdFrequencyCalibrationEntry 2 }



--     modemProdPgaAttenuationTable ----------------------------------

   modemProdPgaAttenuationTable OBJECT-TYPE
        SYNTAX              SEQUENCE OF    ModemProdPgaAttenuationEntry
        MAX-ACCESS          not-accessible
        STATUS              current
        DESCRIPTION
            "This object shows the PGA attenuation table.
            The value of this object is stored into the NVRAM."
        ::= { modemProdUpstreamCalibration 6 }

   modemProdPgaAttenuationEntry OBJECT-TYPE
        SYNTAX              ModemProdPgaAttenuationEntry
        MAX-ACCESS          not-accessible
        STATUS              current
        DESCRIPTION
             "Each entry contains objects describing attributes for Us
        PGA attenuation index."
        INDEX               { modemProdUsPgaAttenIndex }
        ::= { modemProdPgaAttenuationTable 1 }

   ModemProdPgaAttenuationEntry ::= SEQUENCE {
        modemProdUsPgaAttenIndex          INTEGER,
        modemProdUsPgaAttenPower          Integer32
        }

   modemProdUsPgaAttenIndex  OBJECT-TYPE
        SYNTAX  INTEGER {
            pgaAtten0dB(1),
            pgaAtten2dB(2),
            pgaAtten4dB(3),
            pgaAtten8dB(4),
            pgaAtten16dB(5),
            pgaAtten32dBb(6)
        }
        MAX-ACCESS     not-accessible
        STATUS         current
        DESCRIPTION
            "The value of this object is index represents PGA attenuation.
            The value of this object is stored in the NVRAM."
        ::= { modemProdPgaAttenuationEntry 1 }

   modemProdUsPgaAttenPower  OBJECT-TYPE
        SYNTAX  Integer32
        UNITS   "dBmV"
        MAX-ACCESS  read-only
        STATUS  current
        DESCRIPTION
            "Set power for PGA attenuation value.
            The value of this object is stored in the NVRAM."
        ::= { modemProdPgaAttenuationEntry 2 }



--     modemProdCurrentModeFactorTable ----------------------------------

   modemProdCurrentModeFactorTable OBJECT-TYPE
        SYNTAX              SEQUENCE OF    ModemProdCurrentModeFactorEntry
        MAX-ACCESS          not-accessible
        STATUS              current
        DESCRIPTION
            "This object shows the current mode factor table.
            The value of this object is stored into the NVRAM."
        ::= { modemProdUpstreamCalibration 7 }

   modemProdCurrentModeFactorEntry OBJECT-TYPE
        SYNTAX              ModemProdCurrentModeFactorEntry
        MAX-ACCESS          not-accessible
        STATUS              current
        DESCRIPTION
             "Each entry contains objects describing attributes for Us
        current mode factor index."
        INDEX               { modemProdUsCmfIndex }
        ::= { modemProdCurrentModeFactorTable 1 }

   ModemProdCurrentModeFactorEntry ::= SEQUENCE {
        modemProdUsCmfIndex          INTEGER,
        modemProdUsCmfPower          Integer32
        }

   modemProdUsCmfIndex  OBJECT-TYPE
        SYNTAX         INTEGER (1..7)
        MAX-ACCESS     not-accessible
        STATUS         current
        DESCRIPTION
            "The value of this object is index represents Current Mode Factor.
            The value of this object is stored in the NVRAM."
        ::= { modemProdCurrentModeFactorEntry 1 }

   modemProdUsCmfPower  OBJECT-TYPE
        SYNTAX  Integer32
        UNITS   "dBmV"
        MAX-ACCESS  read-only
        STATUS  current
        DESCRIPTION
            "Set power for Current Mode Factor value.
            The value of this object is stored in the NVRAM."
        ::= { modemProdCurrentModeFactorEntry 2 }


modemProdUsCalibrationUpdateFlash OBJECT-TYPE
        SYNTAX         TruthValue
        MAX-ACCESS     read-write
        STATUS         current
        DESCRIPTION
            "Update upstream calibration flash.
            Always returns False(2), which does nothing."
        ::= { modemProdUpstreamCalibration 8 }


END
