-- $Header: /usr/cvsroot/target/src/wrn/wm/demo/unxagent/sun/agent.mib,v 1.3 2002/02/27 21:33:04 josh Exp $

--______________________________________________________________________
--
--  *** Restricted Rights Legend ***
--
--  The programs and information contained herein are licensed only
--  pursuant to a license agreement that contains use, reverse
--  engineering, disclosure, and other restrictions; accordingly, it
--  is "Unpublished - all rights reserved under the applicable
--  copyright laws".
--
--  Use duplication, or disclosure by the Government is subject to
--  restrictions as set forth in subparagraph (c)(1)(ii) of the Rights
--  in Technical Data and Computer Licensed Programs clause of DFARS
--  52.227 7013.
--
--  Copyright 2000-2001 Wind River Systems, Inc.
--  Copyright 1988-1997 Epilogue Technology Corporation.
--  Copyright 1998 Integrated Systems, Inc.
--  All rights reserved.
--
--  *** Government Use ***
--
--  The Licensed Programs and their documentation were developed at
--  private expense and no part of them is in the public domain.
--
--  The Licensed Programs are "Restricted Computer Software" as that
--  term is defined in Clause 52.227-19 of the Federal Acquisition
--  Regulations (FAR) and are "Commercial Computer Software" as that
--  term is defined in Subpart 227.401 of the Department of Defense
--  Federal Acquisition Regulation Supplement (DFARS).
--
--  (i) If the licensed Programs are supplied to the Department of
--      Defense (DoD), the Licensed Programs are classified as
--      "Commercial Computer Software" and the Government is acquiring
--      only "restricted rights" in the Licensed Programs and their
--      documentation as that term is defined in Clause 52.227
--      7013(c)(1) of the DFARS, and
--
--  (ii) If the Licensed Programs are supplied to any unit or agency
--      of the United States Government other than DoD, the
--      Government's rights in the Licensed Programs and their
--      documentation will be as defined in Clause 52.227-19(c)(2) of
--      the FAR.
--______________________________________________________________________

	ETCAgent-MIB

	FORCE-INCLUDE <stdio.h>
	FORCE-INCLUDE <sys/param.h>
	FORCE-INCLUDE <sys/types.h>
	FORCE-INCLUDE <sys/socket.h>
	FORCE-INCLUDE <netinet/in.h>
	FORCE-INCLUDE <netinet/in_systm.h>
	FORCE-INCLUDE <netinet/ip.h>
	FORCE-INCLUDE <netinet/ip_icmp.h>
	FORCE-INCLUDE <net/if.h>
	FORCE-INCLUDE <wrn/wm/demo/if_ether.h>
	FORCE-INCLUDE <wrn/wm/snmp/engine/asn1.h>
	FORCE-INCLUDE <wrn/wm/snmp/engine/mib.h>
	FORCE-INCLUDE <wrn/wm/snmp/engine/snmpdefs.h>
	FORCE-INCLUDE <wrn/wm/snmp/engine/snmp.h>
	FORCE-INCLUDE <wrn/wm/snmp/engine/snmpstat.h>
	FORCE-INCLUDE "general.h"
	FORCE-INCLUDE "snmpvars.h"
	FORCE-INCLUDE "mibhand.h"

	-- MIB file for Sun OS 4.x

	EXCLUDE egp

	DEFINITIONS ::= BEGIN

	IMPORTS
	    OBJECT-TYPE
		FROM RFC-1212
	    mgmt
		FROM RFC1155-SMI
	    system, interfaces, ifEntry, at, atEntry, ipNetToMediaEntry
		FROM RFC1213-MIB
            snmpModules, enterprises, MODULE-IDENTITY
	        FROM SNMPv2-SMI;

etcUnixAgentCTL	MODULE-IDENTITY
	LAST-UPDATED "9804200000Z"
	ORGANIZATION "Integrated Systems Inc"
	CONTACT-INFO "support-email: support@epilogue.com
                 "
	DESCRIPTION  "Control information for v3 mibs"
	::= { enterprises 12 10 2 }

	-- object types

	-- set up MIB-wide defaults
	-- all functions can use %n for object name and
	-- %t for object type, %p for parent name,
	-- %d for name of default-bearing node and %% for %
	mib-2 OBJECT-TYPE
		DEFAULT test-function-async	it_exists_async
		DEFAULT	set-function-async	set_%n
		DEFAULT	get-function-async	get_%n
		DEFAULT	next-function-async	std_next_async
		DEFAULT cookie		(char *) 0
		::= { mgmt 1 }

	-- the System group
	sysDescr OBJECT-TYPE
		DEFAULT	get-function-async	get_string_async
		DEFAULT	cookie		snmp_%n
		::= { system 1 }

	sysObjectID OBJECT-TYPE
		DEFAULT get-function-async	get_object_identifier_async
		DEFAULT cookie		(char *) &snmp_%n
		::= { system 2 }

	sysContact OBJECT-TYPE
		DEFAULT get-function-async	get_string_async
		DEFAULT test-function-async	test_%n
		DEFAULT cookie		(char *) snmp_%n
		::= { system 4 }

	sysLocation OBJECT-TYPE
		DEFAULT get-function-async	get_string_async
		DEFAULT cookie		(char *) snmp_%n
		::= { system 6 }

	-- the Interfaces table

	ifTable OBJECT-TYPE
		DEFAULT get-function-async	iftable_get
		DEFAULT test-function-async	iftable_test
		DEFAULT set-function-async	null_set_async
		DEFAULT next-function-async	iftable_next
		DEFAULT cookie		(char *) 0
		::= { interfaces 2 }

	ifAdminStatus OBJECT-TYPE
		DEFAULT set-function-async	iftable_set
		::= { ifEntry 7 }

	-- the Address Translation group (deprecated)

	atTable OBJECT-TYPE
		DEFAULT get-function-async	arptable_get
		DEFAULT test-function-async	arptable_test
		DEFAULT set-function-async	null_set_async
		DEFAULT next-function-async	arptable_next
		DEFAULT cookie		(char *) 0
		::= { at 1 }

	atPhysAddress OBJECT-TYPE
		DEFAULT set-function-async	set_atPhysAddress
		::= { atEntry 2 }

	-- the IP group
	ip OBJECT-TYPE
		DEFAULT get-function-async	get_ip_info
		::= { mib-2 4 }

	-- the IP Interface table

	ipAddrTable OBJECT-TYPE
		DEFAULT	get-function-async	ipAdEntTable_get
		DEFAULT next-function-async	ipAdEntTable_next
		DEFAULT cookie		(char *) 0
		::= { ip 20 }

	-- the IP Routing table

	ipRouteTable OBJECT-TYPE
		DEFAULT get-function-async	ipRouteTable_get
		DEFAULT set-function-async	ipRouteTable_set
		DEFAULT test-function-async	ipRouteTable_test
		DEFAULT next-function-async	ipRouteTable_next
		DEFAULT cookie		(char *) 0
		::= { ip 21 }

	-- the IP Address Translation tables

	ipNetToMediaTable OBJECT-TYPE
		DEFAULT test-function-async	n2mtable_test
		DEFAULT	get-function-async	n2mtable_get
		DEFAULT set-function-async	null_set_async
		DEFAULT next-function-async	n2mtable_next
		DEFAULT cookie		(char *) 0
		::= { ip 22 }

	ipNetToMediaPhysAddress OBJECT-TYPE
		DEFAULT set-function-async	set_n2mPhysAddress
		::= { ipNetToMediaEntry 2 }

	ipNetToMediaType OBJECT-TYPE
		DEFAULT set-function-async	set_n2mType
		::= { ipNetToMediaEntry 4 }

	-- the ICMP group
	icmp OBJECT-TYPE
		DEFAULT get-function-async	get_icmp_info
		::= { mib-2 5 }

	-- the TCP group

	tcp OBJECT-TYPE
		DEFAULT get-function-async	tcpinfo_get
		::= { mib-2 6 }

	tcpCurrEstab OBJECT-TYPE
		DEFAULT get-function-async	get_%n
		::= { tcp 9 }
  
	-- the TCP connections table

	tcpConnTable OBJECT-TYPE
		DEFAULT	get-function-async	tcptable_get
		DEFAULT set-function-async	null_set_async
		DEFAULT next-function-async	tcptable_next
		::= { tcp 13 }

	-- the UDP group

	udp OBJECT-TYPE
		DEFAULT get-function-async	udpinfo_get
		::= { mib-2 7 }

	-- the UDP listener table

	udpTable OBJECT-TYPE
		DEFAULT get-function-async	udptable_get
		DEFAULT next-function-async	udptable_next
		::= { udp 5 }

	-- the SNMP group

	snmp OBJECT-TYPE
		DEFAULT get-function-async	get_uint_async
		DEFAULT cookie		(char *) &snmp_stats.%n
		::= { mib-2 11 }

	snmpEnableAuthenTraps OBJECT-TYPE
		DEFAULT get-function-async	get_snmpEnableAuthTraps
		DEFAULT set-function-async	set_snmpEnableAuthTraps
		DEFAULT cookie 		(char *) 0
		::=  { snmp 30 }

	snmpMIB	       OBJECT IDENTIFIER ::= { snmpModules 1 }

        snmpMIBObjects OBJECT IDENTIFIER ::= { snmpMIB 1 }

        snmpSet        OBJECT IDENTIFIER ::= { snmpMIBObjects 6 }

        snmpSetSerialNo OBJECT-TYPE
		DEFAULT test-function-async	test_TestAndIncr_async
		DEFAULT	set-function-async	set_TestAndIncr_async
		DEFAULT	get-function-async	get_TestAndIncr_async
		DEFAULT	next-function-async	std_next_async
		DEFAULT cookie		(char *) &%n
		::= { snmpSet 1 }
 	END
