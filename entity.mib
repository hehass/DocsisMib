-- $Header: /usr/cvsroot/target/src/wrn/wm/demo/snmpctls/entity.mib,v 1.1 2002/05/23 18:51:12 josh Exp $

-- Control file for the Entity MIB (RFC 2737)

--______________________________________________________________________
--
--  *** Restricted Rights Legend ***
--
--  The programs and information contained herein are licensed only
--  pursuant to a license agreement that contains use, reverse
--  engineering, disclosure, and other restrictions; accordingly, it
--  is "Unpublished - all rights reserved under the applicable
--  copyright laws".
--
--  Use duplication, or disclosure by the Government is subject to
--  restrictions as set forth in subparagraph (c)(1)(ii) of the Rights
--  in Technical Data and Computer Licensed Programs clause of DFARS
--  52.227 7013.
--
--  Copyright 2002 Wind River Systems, Inc.
--  All rights reserved.
--
--  *** Government Use ***
--
--  The Licensed Programs and their documentation were developed at
--  private expense and no part of them is in the public domain.
--
--  The Licensed Programs are "Restricted Computer Software" as that
--  term is defined in Clause 52.227-19 of the Federal Acquisition
--  Regulations (FAR) and are "Commercial Computer Software" as that
--  term is defined in Subpart 227.401 of the Department of Defense
--  Federal Acquisition Regulation Supplement (DFARS).
--
--  (i) If the licensed Programs are supplied to the Department of
--      Defense (DoD), the Licensed Programs are classified as
--      "Commercial Computer Software" and the Government is acquiring
--      only "restricted rights" in the Licensed Programs and their
--      documentation as that term is defined in Clause 52.227
--      7013(c)(1) of the DFARS, and
--
--  (ii) If the Licensed Programs are supplied to any unit or agency
--      of the United States Government other than DoD, the
--      Government's rights in the Licensed Programs and their
--      documentation will be as defined in Clause 52.227-19(c)(2) of
--      the FAR.
--______________________________________________________________________

ETC-ENTITY-MIB

FORCE-INCLUDE <wrn/wm/snmp/engine/auxmth.h>
FORCE-INCLUDE <wrn/wm/snmp/engine/entlogic.h>

EXCLUDE entityPhysical
EXCLUDE entityMapping

DEFINITIONS ::= BEGIN

IMPORTS
	mib-2, OBJECT-TYPE, MODULE-IDENTITY
		FROM SNMPv2-SMI;

entityMIB OBJECT-TYPE
    DEFAULT get-function-async -stub
    DEFAULT next-function-async -stub
    DEFAULT test-function-async -stub
    DEFAULT set-function-async -stub
    ::= { mib-2 47 }

entityMIBObjects OBJECT-TYPE
	::= { entityMIB 1 }

entityLogical OBJECT-TYPE
	::= { entityMIBObjects 2 }

entLogicalTable OBJECT-TYPE
	::= { entityLogical 1 }

entLogicalEntry OBJECT-TYPE
	::= { entLogicalTable 1 }

entLogicalIndex OBJECT-TYPE
	::= { entLogicalEntry 1 }

entLogicalDescr OBJECT-TYPE
	::= { entLogicalEntry 2 }

entLogicalType OBJECT-TYPE
	::= { entLogicalEntry 3 }

entLogicalCommunity OBJECT-TYPE
	::= { entLogicalEntry 4 }

entLogicalTAddress OBJECT-TYPE
	::= { entLogicalEntry 5 }

entLogicalTDomain OBJECT-TYPE
	::= { entLogicalEntry 6 }

entLogicalContextEngineID OBJECT-TYPE
	::= { entLogicalEntry 7 }

entLogicalContextName OBJECT-TYPE
	::= { entLogicalEntry 8 }

entityGeneral OBJECT-TYPE
	::= { entityMIBObjects 4 }

entLastChangeTime OBJECT-TYPE
	::= { entityGeneral 1 }

END
