-- $Header: /usr/cvsroot/target/src/wrn/wm/demo/snmpctls/v1_exc.mib,v 1.1.1.1 2001/11/05 17:49:10 tneale Exp $

-- Control file to remove SNMPv1 stats objects from a SNMPv2-only agent

--______________________________________________________________________
--
--  *** Restricted Rights Legend ***
--
--  The programs and information contained herein are licensed only
--  pursuant to a license agreement that contains use, reverse
--  engineering, disclosure, and other restrictions; accordingly, it
--  is "Unpublished - all rights reserved under the applicable
--  copyright laws".
--
--  Use duplication, or disclosure by the Government is subject to
--  restrictions as set forth in subparagraph (c)(1)(ii) of the Rights
--  in Technical Data and Computer Licensed Programs clause of DFARS
--  52.227 7013.
--
--  Copyright 2000-2001 Wind River Systems, Inc.
--  Copyright 1988-1997 Epilogue Technology Corporation.
--  Copyright 1998 Integrated Systems, Inc.
--  All rights reserved.
--
--  *** Government Use ***
--
--  The Licensed Programs and their documentation were developed at
--  private expense and no part of them is in the public domain.
--
--  The Licensed Programs are "Restricted Computer Software" as that
--  term is defined in Clause 52.227-19 of the Federal Acquisition
--  Regulations (FAR) and are "Commercial Computer Software" as that
--  term is defined in Subpart 227.401 of the Department of Defense
--  Federal Acquisition Regulation Supplement (DFARS).
--
--  (i) If the licensed Programs are supplied to the Department of
--      Defense (DoD), the Licensed Programs are classified as
--      "Commercial Computer Software" and the Government is acquiring
--      only "restricted rights" in the Licensed Programs and their
--      documentation as that term is defined in Clause 52.227
--      7013(c)(1) of the DFARS, and
--
--  (ii) If the Licensed Programs are supplied to any unit or agency
--      of the United States Government other than DoD, the
--      Government's rights in the Licensed Programs and their
--      documentation will be as defined in Clause 52.227-19(c)(2) of
--      the FAR.
--______________________________________________________________________


ETC-v2-exclude-mib

EXCLUDE snmpOutPkts
EXCLUDE snmpInTooBigs
EXCLUDE snmpInNoSuchNames
EXCLUDE snmpInBadValues
EXCLUDE snmpInReadOnlys
EXCLUDE snmpInGenErrs
EXCLUDE snmpInTotalReqVars
EXCLUDE snmpInTotalSetVars
EXCLUDE snmpInGetRequests
EXCLUDE snmpInGetNexts
EXCLUDE snmpInSetRequests
EXCLUDE snmpInGetResponses
EXCLUDE snmpInTraps
EXCLUDE snmpOutTooBigs
EXCLUDE snmpOutNoSuchNames
EXCLUDE snmpOutBadValues
EXCLUDE snmpOutGenErrs
EXCLUDE snmpOutGetRequests
EXCLUDE snmpOutGetNexts
EXCLUDE snmpOutSetRequests
EXCLUDE snmpOutGetResponses
EXCLUDE snmpOutTraps

DEFINITIONS ::= BEGIN
END
