ARRIS-ROUTER-DEVICE-MIB DEFINITIONS ::= BEGIN

IMPORTS
   MODULE-IDENTITY, OBJECT-TYPE, Integer32, Unsigned32, Counter32, Counter64,
   NOTIFICATION-TYPE, OBJECT-IDENTITY
      FROM SNMPv2-SMI
   InetAddress,
   InetAddressType,
   InetAddressIPv6,
   InetAddressPrefixLength
      FROM INET-ADDRESS-MIB
   ifIndex
      FROM IF-MIB
   arrisProdIdRouter
      FROM ARRIS-MIB
   TruthValue, DisplayString, DateAndTime, MacAddress, RowStatus, PhysAddress
      FROM SNMPv2-TC
   DscpOrAny
      FROM DIFFSERV-DSCP-TC
   OBJECT-GROUP, MODULE-COMPLIANCE, NOTIFICATION-GROUP
	  FROM SNMPv2-CONF;

   arrisRouterMib MODULE-IDENTITY
      LAST-UPDATED    "201706080000Z" -- Jun 08, 2017
      ORGANIZATION    "ARRIS Broadband"
      CONTACT-INFO    "ARRIS Broadband
                       3871 Lakefield Drive
                       Suite 300
                       Suwanee, GA 30024-1242
                       U.S.A."
      DESCRIPTION
       "This MIB module supplies the basic proprietary (ARRIS-specific)
        management objects for ARRIS eRouter/router devices."

    -- Revision history
	REVISION "201706080000Z" -- Jun 08, 2017
		DESCRIPTION
		"Add arrisRouterWiFiApplySettings to { arrisRouterWirelessCfg 1001 }"
    REVISION "201703300000Z" -- Mar 30, 2017
		DESCRIPTION
		"Add arrisRouterSamKnowsMgmt to { arrisRouterMibObjects 14 }"
	REVISION "201702210000Z" -- February 21,2017
		DESCRIPTION
		"Add MIB arrisRouterWiFi50ExtensionChannel to { arrisRouterWiFi50RadioSettings 37 }
		Add MIB arrisRouterPingDSCP to { arrisRouterPingMgmt 22 }"
	REVISION "201701310000Z" -- February 06, 2017
		DESCRIPTION
		"Add MIB arrisRouterWiFiRadioStatsTxDropped to { arrisRouterWiFiRadioStatsEntry 11 }
		Add MIB arrisRouterWiFiRadioStatsRxDropped to { arrisRouterWiFiRadioStatsEntry 12 }
		Add MIB arrisRouterWiFiRadioStatsTxOffer to { arrisRouterWiFiRadioStatsEntry 13 }
		Add MIB arrisRouterWiFiRadioStatsRxOffer to { arrisRouterWiFiRadioStatsEntry 14 }
		Add MIB arrisRouterWiFiRadioStatsTxErrorRate to { arrisRouterWiFiRadioStatsEntry 15 }
		Add MIB arrisRouterWiFiRadioStatsRxFailed to { arrisRouterWiFiRadioStatsEntry 16 }
		Add MIB arrisRouterWiFiRadioStatsTxOfferBytes to { arrisRouterWiFiRadioStatsEntry 17 }
		Add MIB arrisRouterWiFiRadioStatsRxOfferBytes to { arrisRouterWiFiRadioStatsEntry 18 }
		Add arrisRouterWiFiClientInfoVlanId to { arrisRouterWiFiClientInfoEntry 38 }"
	REVISION "201701050000Z" -- Jan 05, 2017
		DESCRIPTION
		"Add arrisRouterUPnPRuleTable to { arrisRouterFWCfg 53 }"
	REVISION "201701050000Z" -- Jan 05, 2017
		DESCRIPTION
		"Add arrisRouterDSLiteProvisioningStatus to { arrisRouterDSLiteWanObjects 10 }
		Add arrisRouterDSLiteOperationalStatus to { arrisRouterDSLiteWanObjects 11 }"
	REVISION "201612230000Z" -- Dec 23, 2016
		DESCRIPTION
		"Add arrisRouterLanIgmpProxyLLQI to { arrisRouterLanConfig 24 }"
	REVISION "201612140000Z" -- December 14,2016
		DESCRIPTION
		"Add MIB Tree arrisRouterStatsMgmt to { arrisRouterMibObjects 13 }
		Add MIB Object arrisRouterWiFiStatsObjects to { arrisRouterStatsMgmt 1}
		Add MIB Table arrisRouterWiFiSSIDStatsTable to {arrisRouterWiFiStatsObjects 1}
		Add MIB Table arrisRouterWiFiRadioStatsTable to {arrisRouterWiFiStatsObjects 2}
		Add MIB Table arrisRouterTunnelStatsTable to  { arrisRouterStatsMgmt  2 }
		Add MIB arrisRouterWiFiSSIDStatsTxOkBytes to { arrisRouterWiFiSSIDStatsEntry 1}
		Add MIB arrisRouterWiFiSSIDStatsRxOkBytes to { arrisRouterWiFiSSIDStatsEntry 2}
		Add MIB arrisRouterWiFiSSIDStatsTxOk to { arrisRouterWiFiSSIDStatsEntry 3}
		Add MIB arrisRouterWiFiSSIDStatsRxOk to { arrisRouterWiFiSSIDStatsEntry 4}
		Add MIB arrisRouterWiFiRadioStatsTxOk to { arrisRouterWiFiRadioStatsEntry 1 }
		Add MIB arrisRouterWiFiRadioStatsTxOkBytes to { arrisRouterWiFiRadioStatsEntry 2 }
		Add MIB arrisRouterWiFiRadioStatsTxFailed to { arrisRouterWiFiRadioStatsEntry 3 }
		Add MIB arrisRouterWiFiRadioStatsMgtTxOk to { arrisRouterWiFiRadioStatsEntry 4 }
		Add MIB arrisRouterWiFiRadioStatsMgtTxFailed to {arrisRouterWiFiRadioStatsEntry 5 }
		Add MIB arrisRouterWiFiRadioStatsTxbyrate to { arrisRouterWiFiRadioStatsEntry 6 }
		Add MIB arrisRouterWiFiRadioStatsRxOk to  { arrisRouterWiFiRadioStatsEntry 7 }
		Add MIB arrisRouterWiFiRadioStatsRxOkBytes to { arrisRouterWiFiRadioStatsEntry 8 }
		Add MIB arrisRouterWiFiRadioStatsMgtRxOk to {arrisRouterWiFiRadioStatsEntry 9 }
		Add MIB arrisRouterWiFiRadioStatsRxbyrate to {arrisRouterWiFiRadioStatsEntry 10 }
		Add MIB arrisRouterTunnelStatstunnelEngine to { arrisRouterTunnelStatsEntry 1 }
		Add MIB arrisRouterTunnelStatstunnel to { arrisRouterTunnelStatsEntry 2 }
		Add MIB arrisRouterTunnelStatsuas to {arrisRouterTunnelStatsEntry 3 }
		Add MIB arrisRouterTunnelStatsrxPkts to {arrisRouterTunnelStatsEntry 4 }
		Add MIB arrisRouterTunnelStatstxPkts to {arrisRouterTunnelStatsEntry 5 }
		Add MIB arrisRouterTunnelStatsrxMBytes to {arrisRouterTunnelStatsEntry 6 }
		Add MIB arrisRouterTunnelStatstxMBytes to {arrisRouterTunnelStatsEntry 7 }
		Add MIB arrisRouterTunnelStatsdownEvents to {arrisRouterTunnelStatsEntry 8 }
		Add MIB arrisRouterBssDisableLegacyRate to { arrisRouterBSSEntry 26  }
		Add MIB arrisRouterWiFiPhysicalChannelStats5GEnable to { arrisRouterWiFiPhysicalChannelStats 7 }"
	REVISION "201612070000Z" -- Dec 07, 2016
		DESCRIPTION
		"Change arrisRouterWiFiGreenModeEnable to default false
		Change arrisRouterWiFi50GreenModeEnable to default false
		Change arrisRouterLanEthernetGreenModeEnable to default false"
	REVISION "201612010000Z" -- Dec 1, 2016
		DESCRIPTION
		"Add arrisRouterFWTr69PopulateEnabled to { arrisRouterFWCfg 52 }"
	REVISION "201611150000Z" -- November 15, 2016
		DESCRIPTION
		"Add MIB arrisRouterWiFiGreenModeEnable to { arrisRouterWirelessCfg 107 }
		Add MIB arrisRouterWiFiGreenModeStatus to { arrisRouterWirelessCfg 108 }
		Add MIB arrisRouterWiFi50GreenModeEnable to { arrisRouterWiFi50RadioSettings 35 }
		Add MIB arrisRouterWiFi50GreenModeStatus to { arrisRouterWiFi50RadioSettings 36 }
		Add MIB arrisRouterLanEthernetGreenModeEnable to { arrisRouterLanConfig 22 }
		Add MIB arrisRouterLanEthernetGreenModeStatus to { arrisRouterLanConfig 23 }"
	REVISION "201611090000Z" -- Nov 09, 2016
		DESCRIPTION
		"Add MIB arrisRouterSTASteerCmd table and arrisRouterSTASteerBlacklistCmd table"
	REVISION "201610260000Z" -- October 26, 2016
		DESCRIPTION
		"Added values wpsResultOverlap(7), wpsResultTimedOut(8), wpsResultInProgress(9) for
		mibs arrisRouterWpsResultStatus and arrisRouterWps50ResultStatus."
	REVISION "201610250000Z" -- October 25, 2016
		DESCRIPTION
		"Add MIB arrisRouterWiFiMgmtFramePower to { arrisRouterWirelessCfg 83 }
		Add MIB arrisRouterWiFi50MgmtFramePower to { arrisRouterWiFi50RadioSettings 34 }
		Change MIB arrisRouterWiFi50AutoChannelList to { arrisRouterWiFi50RadioSettings 33 }"
	REVISION "201610200000Z" -- Oct 20, 2016
		DESCRIPTION
		"Add MIB arrisRouterRIPRoutedExtSubnetTable"
	REVISION "201610070000Z" -- Oct 7, 2016
		DESCRIPTION
		"Add arrisRouterTimeZoneId MIB to { arrisRouterSysCfg 69 } and arrisRouterDaylightSaving MIB to { arrisRouterSysCfg 70 }"
	REVISION "201610030000Z" -- October 3, 2016
		DESCRIPTION
		"Add arrisRouterStaticRouting table"
	REVISION "201609010000Z" -- September 01, 2016
		DESCRIPTION
		"Add MIB arrisRouterTraceRtNumberofTries to { arrisRouterTraceRtMgmt 11 }
		Add MIB arrisRouterAdvancedRadiusCfgSettingsPMKCacheInterval to { arrisRouterAdvancedRadiusCfgSettingsEntry 6 }
		Add MIB arrisRouterWiFiClientHighWatermarkThreshold to { arrisRouterBSSEntry 21 }
		Add MIB arrisRouterWiFiClientHighWatermarkThresholdReached to { arrisRouterBSSEntry 22 }
		Add MIB arrisRouterWiFiClientHighWatermark to { arrisRouterBSSEntry 23 }
		Add MIB arrisRouterWiFiClientHighWatermarkDate to { arrisRouterBSSEntry 24 }
		Add MIB arrisRouterBssBeaconRate to { arrisRouterBSSEntry 25 }"
	REVISION "201608240000Z" -- August 24, 2016
		DESCRIPTION
		"Add MIB arrisRouterWiFiAutoChannelList to { arrisRouterWirelessCfg 79 }
		Add MIB arrisRouterWiFi50AutoChannelList to { arrisRouterWiFi50RadioSettings 31 }
		Add MIB arrisRouterWiFi50StatsGatheringEnable to { arrisRouterWiFi50RadioSettings 32 }"
	REVISION "201608090000Z" -- Aug 09, 2016
		DESCRIPTION
		"Added arrisRouterWiFi50GUIDFSEn"
	REVISION "201607070000Z" -- July 7, 2016
		DESCRIPTION
		"Add arrisRouterWanDHCPOpt61Ctl MIB"
	REVISION "201607060000Z" -- July 06, 2016
		DESCRIPTION
		"Add MTK DBC related Band Steering MIBs"
	REVISION "201607010000Z" -- July 01, 2016
		DESCRIPTION
		"Changed arrisRouterWiFiTransmitPowerInDecibel from arrisRouterWirelessCfg 71 to arrisRouterWirelessCfg 76
		Changed arrisRouterWiFi50TransmitPowerInDecibel from arrisRouterWiFi50RadioSettings 29 to arrisRouterWiFi50RadioSettings 30
		Changed arrisRouterRadiusSecondaryTable from arrisRouterWirelessCfg 72 to arrisRouterWirelessCfg 78"
	REVISION "201606220000Z" -- June 22, 2016
		DESCRIPTION
		"Add arrisRouterWanRtspUdpTimeout  and arrisRouterWanRtspUdpStreamTimeout"
	REVISION "201604250000Z" -- June 20, 2016
		DESCRIPTION
		"Merge MIBs from OG1600 branch to Dev1 branch"
	REVISION "201606150000Z" -- June 15, 2016
		DESCRIPTION
		"Add arrisRouterLanEtherPortEEE to { arrisRouterLanEtherPortEntry 8 }"
	REVISION "201606060000Z" -- June 06, 2016
		DESCRIPTION
		"Add arrisRouterFirstInstallRedirectEnable to { arrisRouterSysCfg 68 }"
	REVISION "201606020000Z" -- June 02, 2016
		DESCRIPTION
		"Add MIB arrisRouterAuthDefaultAdminPassword {arrisRouterAuthEntry 7}"
	REVISION "201605160000Z" -- May 16, 2016
		DESCRIPTION
		"Add MIB arrisRouterDSLiteIPv6FragEnabled to { arrisRouterDSLiteWanObjects 9 }"
	REVISION "201605040000Z" -- May 4, 2016
		DESCRIPTION
		"Add arrisRouterWifiLogs to { arrisRouterWirelessCfg 100 }"
	REVISION "201604220000Z" -- Apr 22, 2016
		DESCRIPTION
		"Move arrisRouterFWIPFilterRuleTr69LastInstance from { arrisRouterFWCfg 48 } to { arrisRouterFWCfg 51 }"
	REVISION "201604220000Z" -- April 22, 2016
		DESCRIPTION
		"Add MIB arrisRouterSoftGreDHCPOption60Enable to { arrisRouterSoftGreSSIDEntry 4 }"
	REVISION "201604190000Z" -- April 19, 2016
		DESCRIPTION
		"Add arrisRouterAdvAirtimeCtrl to { arrisRouterAirtimeCtrlCfg 100 }
		Add arrisRouterAdvAirtimeBSSWeight to { arrisRouterAirtimeCtrlCfg 101 }
		Add arrisRouterAdvAirtimeSTAWeight to {arrisRouterAirtimeCtrlCfg 102 }"
	REVISION "201604150000Z" -- Apr 15, 2016
		DESCRIPTION
		"Add arrisRouterTrustedDeviceTr69InstanceID and arrisRouterTrustedDeviceTr69LastInstance"
	REVISION "201603300000Z" -- Mar 30, 2016
		DESCRIPTION
		"Add arrisRouterFWMACFilterAllowListRuleTr69LastInstance, arrisRouterFWMACFilterDenyListRuleTr69LastInstance, arrisRouterFWMACFilterRuleTr69InstanceID, arrisRouterFWMACFilterTimeTr69InstanceID and arrisRouterFWMACFilterTimeTr69LastInstance for TR069 instance tracking"
	REVISION "201603220000Z" -- Mar 22, 2016
		DESCRIPTION
		"Add arrisRouterFWMACFilterTODExt to { arrisRouterFWCfg 48 }"
	REVISION "201603220000Z" -- Mar 22, 2016
		DESCRIPTION
		"Add MIB arrisRouterAdvancedRadiusCfgSettingsPMKLifetime and arrisRouterAdvancedRadiusCfgSettingsPMKCaching"
	REVISION "201603220000Z" -- Mar 22, 2016
		DESCRIPTION
		"Add arrisRouterBlackListWebSiteTr69LastInstance, arrisRouterBlackListTimeTr69LastInstance, arrisRouterBlackListWebSiteTr69InstanceID, arrisRouterBlackListTimeTr69InstanceID, arrisRouterWhiteListWebSiteTr69LastInstance, arrisRouterWhiteListTimeTr69LastInstance, arrisRouterWhiteListWebSiteTr69InstanceID, arrisRouterWhiteListTimeTr69InstanceID for TR069 instance tracking"
	REVISION "201603150000Z" -- Mar 15, 2016
		DESCRIPTION
		"Add arrisRouterMSOConfigPersistNoPrecedence MIB"
	REVISION "201603140000Z" -- Mar 14, 2016
		DESCRIPTION
		"Add arrisRouterKeywordBlkFilterTr69LastInstance, arrisRouterKeywordBlkTimeTr69LastInstance, arrisRouterKeywordBlkFilterTr69InstanceID and arrisRouterKeywordBlkTimeTr69InstanceID for TR069 instance tracking"
	REVISION "201603080000Z" -- Mar 8, 2016
		DESCRIPTION
		"Add MIB arrisRouterSoftGreSSIDEnable to { arrisRouterSoftGreSSIDEntry 3 }"
	REVISION "201602230000Z" -- Feb 23, 2016
		DESCRIPTION
		"Add arrisRouterFWIPFilterRuleTr69LastInstance, arrisRouterFWIPFilterTimeTr69LastInstance, arrisRouterFWIPFilterRuleTr69InstanceID and arrisRouterFWIPFilterTimeTr69InstanceID for TR069 instance tracking"
	REVISION "201602020000Z" -- Feb 02, 2016
		DESCRIPTION
		"Change arrisRouterBandSteerSteerProhibitTime to arrisRouterBandSteerProhibitTime"
	REVISION "201601290000Z" -- Jan 29, 2016
		DESCRIPTION
		"Change the range of arrisRouterBandSteerUtilSamplePeriod to 1 ~ 90"
	REVISION "201601280000Z" -- Jan 28, 2016
		DESCRIPTION
		"Changed MIB arrisRouterExceptionListIndex range limit from 16 to 30 "
	REVISION "201601180000Z" -- Jan 18, 2016
		DESCRIPTION
		"Add a new MIB arrisRouterFWDDNSHttpsSupport."
	REVISION "201601140000Z" -- Jan 14, 2016
		DESCRIPTION
		"Added arrisRouterBandSteering table"
	REVISION "201512290000Z" -- Dec 29, 2015
		DESCRIPTION
		"Add MIB arrisRouterLanMaxNatSessions to { arrisRouterLanConfig 20 }"
	REVISION "201511260000Z" -- Nov 26, 2015
		DESCRIPTION
		"Add MIB arrisRouterFWIPv6BlockMtaICMPNS to { arrisRouterFWIPv6Security 9 }"
	REVISION "201510130000Z" -- Oct 13, 2015
		DESCRIPTION
		"Add MIB arrisRouterSoftGreRadiusAcctEnabled to { arrisRouterSoftGreWanEntry 42 }"
	REVISION "201508180000Z" -- Oct 5, 2015
		DESCRIPTION
		"Add new MIB arrisRouterDBConversionStatus and change MIB arrisRouterCSRActiveTimeout to { arrisRouterSysCfg 66 }"
	REVISION "201509130000Z" -- Sep 13, 2015
		DESCRIPTION
		"Add MIB arrisRouterUsbConfig to { arrisRouterMibObjects 12 }"
	REVISION "201508180000Z" -- Aug 18, 2015
		DESCRIPTION
		"Add MIB arrisRouterSoftGreRemoteIdUseCMMac to { arrisRouterSoftGreWanEntry 41 }"
	REVISION "201507300000Z" -- Jul 30, 2015
		DESCRIPTION
		"Add MIB arrisRouterFWIPFilterExtend to { arrisRouterFWCfg 47 }"
	REVISION "201506040000Z" -- Jul 28, 2015
		DESCRIPTION
		"Add MIB arrisRouterWpsLockDownStatus  { arrisRouterWPSCfg 16 }
		Add MIB arrisRouterWps50LockDownStatus  { arrisRouterWPS50Cfg 16 } "
	REVISION "201507080000Z" -- July 8, 2015
		DESCRIPTION
		"Add MIB arrisRouterCSRActiveTimeout to { arrisRouterSysCfg 65 }"
	REVISION "201505220000Z" -- May 22, 2015
		DESCRIPTION
		"Add more options for MIB arrisRouterFWDDNSType"
	REVISION "201305220000Z" -- May 22, 2015
		DESCRIPTION
		"Add WPAPSK to arrisRouterBssSecurityMode because P5 GW need this value."
	REVISION "201505210000Z" -- May 21, 2015
		DESCRIPTION
		"Add MIB arrisRouterWiFi50AMSDUEnable"
	REVISION "201505150000Z" -- May 15, 2015
		DESCRIPTION
		"Add MIB arrisRouterPingLog to { arrisRouterPingMgmt 21 }"
	REVISION "201505130000Z" -- May 13, 2015
		DESCRIPTION
		"Add MIB arrisRouterBssStaSteeringEnable to { arrisRouterBSSEntry 16 }
		Add MIB arrisRouterWiFiInterworkingIE to { arrisRouterWirelessCfg 68 }
		Add MIB arrisRouterWiFiBssStaSteering to { arrisRouterWirelessCfg 69 }"
	REVISION "201504280000Z" -- Apr 28, 2015
		DESCRIPTION
		"Add MIB arrisRouterFirewallLogExtTable"
	REVISION "201504270000Z" -- Apr 27, 2015
		DESCRIPTION
		"Add the following new MIBs to the arrisRouterSoftGreWanEntry
		arrisRouterSoftGreRadiusSecondaryServerAddressType-->{ arrisRouterSoftGreWanEntry 36 }
		arrisRouterSoftGreRadiusSecondaryServerAddress-->{ arrisRouterSoftGreWanEntry 37 }
		arrisRouterSoftGreRadiusSecondaryServerPort-->{ arrisRouterSoftGreWanEntry 38 }
		arrisRouterSoftGreRadiusSecondaryKey-->{ arrisRouterSoftGreWanEntry 39 }
		arrisRouterSoftGreRadiusSecondaryReAuthInterval-->{ arrisRouterSoftGreWanEntry 40 }"
	REVISION "201504240000Z" -- Apr 24, 2015
		DESCRIPTION
		"Add the following new MIBs to the arrisRouterSoftGreWanEntry
		arrisRouterSoftGreAcctServerAddressType-->{ arrisRouterSoftGreWanEntry 31 }
		arrisRouterSoftGreAcctServerAddress-->{ arrisRouterSoftGreWanEntry 32 }
		arrisRouterSoftGreAcctServerPort-->{ arrisRouterSoftGreWanEntry 33 }
		arrisRouterSoftGreAcctKey-->{ arrisRouterSoftGreWanEntry 34 }
		arrisRouterSoftGreAcctInterval-->{ arrisRouterSoftGreWanEntry 35 }
		"
	REVISION "201504100000Z" -- Apr 10, 2015
		DESCRIPTION
		"Modify MIB arrisRouterRIPInterface OID from { arrisRouterRIPObjects 19 } to { arrisRouterRIPObjects 23 } and MIB arrisRouterFWSrvTr69LastInstance
		OID from { arrisRouterFWCfg 34 } to { arrisRouterFWCfg 46 } to solve the OID conflict with MG"
	REVISION "201504100000Z" -- Apr 10, 2015
		DESCRIPTION
		"Add MIB arrisRouterFWMacBridgingWebPageEnabled to { arrisRouterFWCfg 41 }"
	REVISION "201504020000Z" -- Apr 2, 2015
		DESCRIPTION
		"Modify MIB arrisRouterCpuSpeed OID from { arrisRouterSysCfg 51 } to { arrisRouterSysCfg 64 } to solve the OID conflict with MG"
	REVISION "201504010000Z" -- Apr 1, 2015
		DESCRIPTION
		"Change MIB name from arrisrouterWifiLowInitRate  to arrisRouterWifiLowInitRate"
	REVISION "201503310000Z" -- Mar 31, 2015
		DESCRIPTION
		"Add MIB arrisRouterAirtimeCtrlCfg to { arrisRouterWirelessCfg 99 }"
	REVISION "201501040000Z" -- Mar 27, 2015
		DESCRIPTION
		"Add a mib arrisRouterLanIPv6RALifetime to {arrisRouterLanConfig 19 }"
	REVISION "201503260000Z" -- Mar 26, 2015
		DESCRIPTION
		"Add a mib arrisRouterDSLiteWanResolvedAddr to {arrisRouterWanConfig 21 }"
	REVISION "201503130000Z" -- Mar 13, 2015
		DESCRIPTION
		"Add MIB arrisRouterSNTPSettings to { arrisRouterSysCfg 17 }"
	REVISION "201503100000Z" -- Mar 10, 2015
		DESCRIPTION
		"remove redundant ArrisRouterFWPortAllowEntry definition which causes mib build error"
	REVISION "201502270000Z" -- Feb 27, 2015
		DESCRIPTION
		"rollback the change for arrisRouterWebAccessLevel in dev1_cn"
	REVISION "201502190000Z" -- Feb 19, 2015
		DESCRIPTION
		"Add a mib arrisRouterDefaultWPAPreSharedKey to { arrisRouterWPAEntry 6 }
		Add a mib arrisRouterDefaultBssSSID to { arrisRouterBSSEntry 15  }"
	REVISION "201502170000Z" -- Feb 17, 2015
		DESCRIPTION
		"Add MIB Table arrisRouterFlapListLANTable,arrisRouterFlapListWLANTable to { arrisRouterFlapListCfg 11  }"
	REVISION "201502130000Z" -- Feb 13, 2015
		DESCRIPTION
		"Add a mib arrisrouterWifiLowInitRate"
	REVISION "201502120000Z" -- Feb 12, 2015
		DESCRIPTION
		"Add new MIBs: arrisRouterExceptionListCount, arrisRouterExceptionListTable,
		arrisRouterExceptionListEntry, arrisRouterExceptionListIndex,
		arrisRouterExceptionListDomain,
		arrisRouterExceptionListStatus"
	REVISION "201502060000Z" -- Feb 06, 2015
		DESCRIPTION
		"Add MIB arrisRouterTroubleshooterEnable to { arrisRouterSysCfg 63 }"
	REVISION "201501300000Z" -- Jan 30, 2015
		DESCRIPTION
		"Changed arrisRouterEmailNetworkCredential to arrisRouterEmailSend"
	REVISION "201501280000Z" -- January 28, 2015
		DESCRIPTION
		"Added arrisRouterSSHAccessWANACL."
	REVISION "201501040000Z" -- Jan 04, 2015
		DESCRIPTION
		"Add a mib arrisRouterSoftGreRadiusTransportInterface to { arrisRouterSoftGreWanEntry 30 }"
	REVISION "201405280000Z" -- May 28, 2014
		DESCRIPTION
		"Added arrisRouterAdvDebugSettings."
	REVISION "201404020000Z" -- April 18, 2014
		DESCRIPTION
		"Add MIB arrisRouterLanBridgeType to { arrisRouterLanConfig 15 }"
	REVISION "201404040000Z" -- April 04, 2014
		DESCRIPTION
	    "Added multicast monitoring OIDs."
	REVISION "201404020000Z" -- April 02, 2014
		DESCRIPTION
		"Add MIB arrisRouterFWMacBridgingWebPageEnabled to { arrisRouterFWCfg 41 }
		 Add MIB arrisRouterFWMacBridgingFunctionEnabled to { arrisRouterFWCfg 42 }
		 Add MIB arrisRouterFWMacBridgingTable to { arrisRouterFWCfg 43 }"
	REVISION "201404010000Z" -- Apr 01, 2014
	    DESCRIPTION
		"Added arrisRouterPrivateWanEnabled."
	REVISION "201403070000Z" -- Mar 07, 2014
		  DESCRIPTION
		  "Change the MIBs in arrisRouterDSLiteWanObjects same as arris_router_tw.mib:
		   Remove MIB arrisRouterDSLiteWanLSNATAddrType,
		   Replace arrisRouterDSLiteWanLSNATAddr with arrisRouterDSLiteWanLSNATIPAddr."
	REVISION "201402280000Z" -- February 28, 2014
	     DESCRIPTION
		"Add arrisRouterDumpDocsisLog."
	REVISION "201312240000Z" -- Dec 24, 2013
		DESCRIPTION
		"Add MIB arrisRouterICtrlHashingKey to { arrisRouterICtrl 13 }"
         REVISION "201312180000Z" -- Dec 18, 2013
		  DESCRIPTION
		  "Add MIB arrisRouterLanMaxIPv6RAInterval to { arrisRouterLanConfig 13 }
		  Add MIB arrisRouterLanMinIPv6RAInterval to { arrisRouterLanConfig 14 }"
         REVISION "201312170000Z" -- December 17, 2013
		DESCRIPTION
	    "Added arrisRouterWiFiACSCLI."
	 REVISION "201312090000Z" -- December 09, 2013
		DESCRIPTION
		"Added arrisRouterWiFiPhysicalChannelDetails and arrisRouterWiFi50PhysicalChannelDetails."
	 REVISION "201311070000Z" -- Nov 07, 2013
		  DESCRIPTION
		  "Add table arrisRouterLanClientDHCPOptionsTable"
		REVISION "201311010000Z" -- Nov 01, 2013
		  DESCRIPTION
		  "Revise the MIB description for arrisRouterWanIPProvMode & arrisRouterLanPassThru"
                REVISION "201310310000Z" -- Oct 31, 2013
			DESCRIPTION
			"Add MIB arrisRouterSoftGreWanStatus to { arrisRouterSoftGreWanEntry 27 }"
		REVISION "201310210000Z" -- Oct 21, 2013
                  DESCRIPTION
                  "Add new mibs for arrisRouterWanCurrentDNSIPAddr,
                   arrisRouterLanEtherPortEnabled, arrisRouterLanEtherPortSpeed,
                   arrisRouterLanEtherPortDuplex, arrisRouterWMMAPSD,
                   arrisRouterRadiusAddress, arrisRouterRadiusPort,
                   arrisRouterRadiusKey, arrisRouterWiFiHTMCS, arrisRouterRIPEnable"
                REVISION "201310170000Z" -- Oct 17, 2013
		  DESCRIPTION
		  "Add MIB arrisRouterWanConnType"
		REVISION "201310090000Z" -- Oct 09, 2013
		  DESCRIPTION
		  "Modify arrisRouterFWIPv6Security's OID to { arrisRouterFWCfg 40 }"
		REVISION "201310070000Z" -- Oct 07, 2013
		  DESCRIPTION
          "Add new Mibs
           1. Add new mibs for remote management
              arrisRouterFWRemoteMgmt, arrisRouterFWRemoteMgmtHttp,
              arrisRouterFWRemoteMgmtHttps, arrisRouterFWRemoteMgmtHttpPort,
              arrisRouterFWRemoteMgmtHttpsPort, arrisRouterFWRemoteMgmtAllowedType,
              arrisRouterFWRemoteMgmtAllowedIPv4, arrisRouterFWRemoteMgmtAllowedIPv6,
              arrisRouterFWRemoteMgmtAllowedStartIPv4, arrisRouterFWRemoteMgmtAllowedEndIPv4,
              arrisRouterFWRemoteMgmtAllowedStartIPv6, arrisRouterFWRemoteMgmtAllowedEndIPv6,
           2. Add new mibs for port Forwarding IPv6
		      arrisRouterFWVirtSrvIP2AddrType
			  arrisRouterFWVirtSrvIP2Addr.
		   3. Add new mibs for IPv6 Firewall security
		      arrisRouterFWIPv6Security
			  arrisRouterFWIPv6SecurityLevel
			  arrisRouterFWIPv6BlockHTTP
              arrisRouterFWIPv6BlockICMP
			  arrisRouterFWIPv6BlockMulticast
			  arrisRouterFWIPv6BlockP2P
              arrisRouterFWIPv6BlockIDENT
			  arrisRouterFWIPv6Enable
			  arrisRouterFWIPv6ResetDefaults
		   4. Add new mibs for DMZ IPv6
		      arrisRouterFWIP2AddrTypeDMZ
			  arrisRouterFWIP2AddrDMZ"

    		REVISION "201310030000Z" -- October 03, 2013
		DESCRIPTION
	    "Added arrisRouterFWExceptionList."
	REVISION "201309170000Z" -- Sep 17, 2013
             DESCRIPTION
             "Add MIB arrisRouterWanForceIGMPVersion."
        REVISION "201309170000Z" -- Sept 17, 2013
          DESCRIPTION
          "Add MIB arrisRouterAdminBridgeOptionDisplay."
		REVISION "201309160000Z" -- September 16, 2013
		DESCRIPTION
		"Added arrisRouterLanArrisDeviceLeaseTime."
        REVISION "201309060000Z" -- Sept 06, 2013
          DESCRIPTION
          "Add MIB arrisrouterWifiClientIdleTimeout."
	REVISION "201308200000Z" -- Aug 20, 2013
             DESCRIPTION
             "Add MIB arrisRouterFWVirtSrvTableEnabled."
	REVISION "201308060000Z" -- Aug 15, 2013
          DESCRIPTION
          "Chnage arrisRouterLanSrvDHCPOptionsTable's OID to 4115.1.20.1.1.2.11"
         REVISION "201308060000Z" -- Aug 6, 2013
          DESCRIPTION
          "Add arrisRouterLanClientLeaseEnd"
	  REVISION "201307290000Z" -- July 29, 2013
             DESCRIPTION
             "Correct the MIB name 'arrisRouterFWDDNSUserHame' to 'arrisRouterFWDDNSUserName'"
    REVISION "201307220000Z" -- July 22, 2013
            DESCRIPTION
             "Add MIB arrisRouterBssMSOSSID0Setting to read the MSO setting to SSID0 enable/disable"
    REVISION "201307220000Z" -- July 22, 2013
             DESCRIPTION
             "Remove arrisRouterWanBridgeModeTCPMSSValue, changed arrisRouterLanSrvDHCPOptionsTable to arrisRouterLanConfig 11"
		REVISION "201307180000Z" -- July 18, 2013
         DESCRIPTION
		"Added a new logging level to arrisRouterLogLevel."
		REVISION "201305230000Z" -- May 23, 2013
         DESCRIPTION
		"Updated range comments for arrisRouterLanLeaseTime."
		REVISION "201304090000Z" -- April 09, 2013
         DESCRIPTION
		"Added arrisRouterFWPortForwardStatus, arrisRouterFWPortForward, and arrisRouterFWPortForwardDelete."
        REVISION "201303150000Z" -- Mar 15, 2013
	      DESCRIPTION
 	      "Add arrisRouterDHCPRelayAgentOption60SSIDEnabled"
        REVISION "201303140000Z" -- Mar 14, 2013
	      DESCRIPTION
        "Add arrisRouterICtrlEnable"
        REVISION "201303220000Z" -- Mar 22, 2013
         DESCRIPTION
         "Add arrisRouterBssMaxWifiClients"
        REVISION "201303180000Z" -- Mar 18, 2013
         DESCRIPTION
         "Add MIB arrisRouterICtrlSetBridgePermanentPort4Enable to enable or disable permanent bridge mode for port 4. It only for CT."
    	  REVISION "201211260000Z" -- November 26, 2012
         DESCRIPTION
         "Added additional parameters for arrisRouterWanInterface."
        REVISION "201211050000Z" -- November 05, 2012
         DESCRIPTION
         "Added arrisRouterWMMCurrentRadio."
        REVISION "201210220000Z" -- October 22, 2012
         DESCRIPTION
         "Added arrisRouterWiFi50PhysicalChannel and arrisRouterWiFi50TxPowerPhysical.
         Added arrisRouterAdvWiFiStatsRadio.
         Added the ability to select the radio for arrisRouterWiFiStartScan."
        REVISION "201208020000Z" -- Aug 02, 2012
        DESCRIPTION
            "Update value of arrisRouterBssSecurityMode to support wpaWpa2Enterprise"
        REVISION "201207310000Z" -- July 31, 2012
        DESCRIPTION
        "Added size params to: arrisRouterDHCPOption43Sub2, arrisRouterDHCPOption43Sub3, arrisRouterESTBDHCPOption43Sub2, arrisRouterESTBDHCPOption43Sub3, arrisRouterDHCPOption60ERouter, arrisRouterDHCPOption60ESTB."
        REVISION "201207230000Z" -- Jul 23, 2012
        DESCRIPTION
            "Update the description of MIB arrisRouterLanPassThru"
        REVISION "201204230000Z" -- Apr. 20, 2012
         DESCRIPTION
            "Add in third pass of SoftGRE MIBs, includes Failover and Radius"
        REVISION "201204030000Z" -- April 3, 2012
        DESCRIPTION
        "Add arrisRouterWiFiAllow40MHzOnlyOperation MIB definition"
        REVISION "201203260000Z" -- Mar 26, 2012
         DESCRIPTION
            "Fix some syntax errors."
        REVISION "201203150000Z" -- Mar 15, 2012
         DESCRIPTION
            "Add in updated VLan and DSCP Mibs for SoftGre"
        REVISION "201203080000Z" -- March 08, 2012
        DESCRIPTION
        "Reduced the number of possible rows in arrisRouterMACAccessTable to 15"
        REVISION "201203070000Z" -- March 07, 2012
        DESCRIPTION
        "Add arrisRouterNATPortFwdTable and arrisRouterNATPortFwdPersistUPnP under new sub-object: arrisRouterNATInfo."
        REVISION "201202290000Z" -- Feb 29, 2012
         DESCRIPTION
            "Add in arrisRouterICtrlHNAPServerPort to iCtrl tree."
        REVISION "201202230000Z" -- Feb 23, 2012
         DESCRIPTION
            "Add in arrisRouterSoftGre settings"
        REVISION "201202150000Z" -- February 21, 2012
        DESCRIPTION
             "Added arrisRouterFWIPFilterAction, arrisRouterFWIPFilterDirection"
        REVISION "201202150000Z" -- February 21, 2012
        DESCRIPTION
        "Reduce parameters for: arrisRouterWanInterface."
        REVISION "201202220000Z" -- Feb 22, 2012
         DESCRIPTION
            "Merge TW/NA mibs into CT MIB file"
        REVISION "201202200000Z" -- Feb 20, 2012
        DESCRIPTION
            "Fix OID for arrisRouterWpsConfigTimeout, arrisRouterWpsSTAPin
             and arrisRouterWpsPushButton MIBs"
        REVISION "201202150000Z" -- February 15, 2012
        DESCRIPTION
             "Added arrisRouterLanPreProvLeaseTime MIB"
        REVISION "201201100000Z" -- January 10, 2012
        DESCRIPTION
            "Updated arrisRouterSystemFlags"
        REVISION "201112090000Z" -- December 09, 2011
        DESCRIPTION
            "Added arrisRouterInboundTrafficLogTable, arrisRouterInboundTrafficLogEntry, arrisRouterInboundTrafficLogIndex, arrisRouterInboundTrafficLogData "
        REVISION "201111300000Z" -- November 30, 2011
        DESCRIPTION
            "Added arrisRouterARPAutoInjectDisable"
        REVISION "201111290000Z" -- November 29, 2011
        DESCRIPTION
        "Added arrisRouterARPObjects"
        REVISION "201111170000Z" -- Nov 17, 2011
         DESCRIPTION
            "Remove arrisRouterWiFiTxPower MIB. No longer supported. Use
	     the arrisRouterWiFiOutputPower MIB instead."
        REVISION "201111160000Z" -- November 16, 2011
        DESCRIPTION
            "Added wireless interference configuration parameters: "
        REVISION "201111150000Z" -- November 15, 2011
        DESCRIPTION
            "Added advanced wireless counters and statistics: arrisRouterAdvanceWirelessStats.
            Added arrisRouterWebAccessWANACL."
        REVISION "201110290000Z" -- October 29, 2011
        DESCRIPTION
            "Added arrisRouterFWIPFilterAction, arrisRouterFWIPFilterDirection."
        REVISION "201110180000Z" -- October 18, 2011
        DESCRIPTION
            "Added arrisRouterSystemFlags."
        REVISION "201110110000Z" -- October 11, 2011
        DESCRIPTION
            "Marked arrisRouterLanClientTable as deprecated.  This table no longer works on the Arris Whole Home Solution Media Gateway. It may still work on other Arris Gateway devices with eRouter.
            arrisRouterLanCurrentClientTable has been added and should now be used.
            To add new static LAN clients, use arrisRouterLanStaticClientTable instead of the deprecated arrisRouterLanClientTable
            Added arrisRouterWiFiUtilityCommand and arrisRouterWiFiUtilityCommandOutput.
            Added arrisRouterClientTrackingEnable.
            Added arrisRouterWiFiPhysicalChannel.
            Added arrisRouterWiFiTxPowerPhysical.
            Added arrisRouterWiFiShortSlotEnhanced.
            Added arrisRouterLanClientLogTable.
            Added arrisRouterWiFiClientInfoTable."
        REVISION "201110060000Z" -- Oct 6, 2011
         DESCRIPTION
            "Added arrisRouterWiFiTxPower and arrisRouterLanNatAlgsEnabled MIB"
         REVISION "201109300000Z" -- September 30, 2011
         DESCRIPTION
            "Added arrisRouterWanDelegatedPrefixLength, arrisRouterWanDelegatedPrefix, arrisRouterDSLiteWanLSNATAddrType, arrisRouterInboundTrafficLogTable, arrisRouterInboundTrafficLogEntry, arrisRouterInboundTrafficLogIndex, arrisRouterInboundTrafficLogData "
         REVISION "201109180000Z" -- September 18, 2011
         DESCRIPTION
            "Added arrisRouterDHCPOption43Sub2, arrisRouterDHCPOption43Sub3, arrisRouterESTBDHCPOption43Sub2, arrisRouterESTBDHCPOption43Sub3"
         REVISION "201109160000Z" -- September 16, 2011
         DESCRIPTION
            "Added arrisRouterDisableResetButton."
	  REVISION "201109060000Z" -- September 06, 2011
                DESCRIPTION
                "Added arrisRouterWiFiRadioControlMode,
		arrisRouterLanMappedInterface,
		arrisRouterLanEnvironmentControl"
	  REVISION "201108300000Z" -- Aug 30, 2011
		DESCRIPTION
		"Added arrisRouterFWBlockFragIPPkts,
		Fix the OID of arrisRouterWebAccessTable."
         REVISION "201108290000Z" -- August 29, 2011
         DESCRIPTION
            "Added arrisRouterWiFiAutoChannelTime and arrisRouterWiFiScan."
         REVISION "201108250000Z" -- August 25, 2011
         DESCRIPTION
          "Added arrisRouterFWEnableLanSNMPWireless, arrisRouterNATDebug, and arrisRouterLanEtherPortHasLink."
	 REVISION "201108220000Z" -- Aug 22, 2011
	 DESCRIPTION
		"Added arrisRouterICtrl OIDs."
	  REVISION "201108180000Z" -- Aug 18, 2011
	  DESCRIPTION
		"Added arrisRouterWebAccessTable.
		Updated Syntax of arrisRouterAuthUserName, arrisRouterAuthPassword and arrisRouterAuthType."
         REVISION "201108170000Z" -- August 17, 2011
         DESCRIPTION
            "Added arrisRouterNATPBypassEnable."
        REVISION "201108160000Z" -- August 16, 2011
         DESCRIPTION
            "Removed arrisRouterTCPAckSuppression.
            Added arrisRouterICtrl OIDs.
            Added interfaces control OID: arrisRouterIPStacks.
            Added arrisRouterWiFiRadioControlMode, arrisRouterLanMappedInterface, arrisRouterLanEnvironmentControl.
            Added arrisRouterEnabledInterfaces and arrisRouterEnabledInterfacesString."
        REVISION "201108070000Z" -- August 07, 2011
         DESCRIPTION
    	   "Added additional oids for IPV6."
        REVISION "201108040000Z" -- August 04, 2011
         DESCRIPTION
            "Changed arrisRouterTACACSAddr back to displaystring and re-adding arrisRouterTACACSIPAddr and added arrisRouterTACACSIPAddrType.
            Added arrisRouterTCPAckSuppression."
        REVISION "201107250000Z" -- July 25, 2011
         DESCRIPTION
            "Added arrisRouterChangeLogFilter."
        REVISION "201107130000Z" -- July 13, 2011
         DESCRIPTION
            "Added arrisRouterLanNatAlgsEnabled
             Added arrisRouterRIPRoutedSubnetTable."
        REVISION "201106130000Z" -- June 13, 2011
         DESCRIPTION
			"Modified arrisRouterEnableLanEtherPrivateWanBlock."
        REVISION "201106090000Z" -- June 09, 2011
         DESCRIPTION
			"Modified arrisRouterBlockNonArrisDevices to handle blocking just MoCA network."
        REVISION "201106020000Z" -- June 02, 2011
         DESCRIPTION
			"Added arrisRouterPrivateWanInterfaceName, arrisRouterPrivateWanMacAddr and arrisRouterPrivateWanCurrentDNSTable."
        REVISION "201106010000Z" -- June 01, 2011
         DESCRIPTION
			"Added arrisRouterTechnicianName."
	REVISION "201105240000Z" -- May 24, 2011
	 DESCRIPTION
		"Modify the arrisRouterWpsDevicePIN from
                 read-write to read-only."
        REVISION "201105170000Z" -- May 17, 2011
         DESCRIPTION
            "Added arrisRouterDHCPLogTable and arrisRouterDHCPLogLevel.
			Added new objects under: arrisRouterPrivateWanObjects."
        REVISION "201105100000Z" -- May 10, 2011
         DESCRIPTION
			"Added dual-mode support to arrisRouterWanInterface."
        REVISION "201105040000Z" -- May 04, 2011
         DESCRIPTION
		 "Added arrisRouterWiFiUseSNForPSK."
	  REVISION "201105050000Z" -- May 5, 2011
		DESCRIPTION
		"Added arrisRouterAuthTable for TG852G/NA/TW"
	  REVISION "201104280000Z" -- April 28, 2011
		DESCRIPTION
		"Removed arrisRouterWiFiEnableRadioNow for TG852G/NA/TW"
        REVISION "201104270000Z" -- April 27, 2011
         DESCRIPTION
			"Changed arrisRouterCustomID to read/write. Added arrisRouterWanInterface."
        REVISION "201104260000Z" -- April 26, 2011
         DESCRIPTION
			"Added arrisRouterWiFiReset.
			Added arrisRouterTrustedDeviceAddrType and arrisRouterTrustedDeviceAddr
			Added arrisRouterTrustedDeviceManagedServicesAddrType and arrisRouterTrustedDeviceManagedServicesAddr."
        REVISION "201104220000Z" -- April 22, 2011
         DESCRIPTION
            "Added arrisRouterFWVirtSrvTableEnabled, arrisRouterFWPortTrigTableEnabled,
                arrisRouterManagedServicesEnabled, arrisRouterManagedSitesEnabled, arrisRouterManagedDevicesEnabled
                arrisRouterTrustedDeviceName
                arrisRouterTrustedDeviceManagedServicesTable
				arrisRouterFWMACFilterHostName."
		REVISION "201104150000Z" -- April 15, 2011
		 DESCRIPTION
			"Added arrisRouterBlockNonArrisDevices."
		REVISION "201104010000Z" -- April 01, 2011
		 DESCRIPTION
			"Changed arrisRouterTACACSAddr to arrisRouterTACACSIPAddr and added arrisRouterTACACSIPAddrType."
		REVISION "201103220000Z" -- March 22, 2011
		 DESCRIPTION
			"Changed name: arrisRouterWanCurrentDNSIPType to arrisRouterWanCurrentDNSIPAddrType and arrisRouterWanStaticDNSIPType to arrisRouterWanStaticDNSIPAddrType."
		REVISION "201103170000Z" -- March 17, 2011
		 DESCRIPTION
			"Added arrisRouterFWEnableNow and arrisRouterFWAllowDestPorts."
	REVISION "201103110000Z" -- March 11, 2011
		DESCRIPTION
		"Added additional columns to the arrisRouterLanTable:
arrisRouterLanClientOnline, arrisRouterLanClientComment,arrisRouterLanClientCustom."
        REVISION "201103100000Z" -- March 10, 2011
         DESCRIPTION
                "Added additional columns to the arrisRouterLanTable: arrisRouterLanClientOnline, arrisRouterLanClientComment, arrisRouterLanClientCustom.
		Removed arrisRouterDeviceUpDownEntry, arrisRouterLanCustomCount, arrisRouterLanCustomTable,
		 arrisRouterWPAReAuthInterval, arrisRouterFWVirtSrvTOD, arrisRouterFWPortTrigTOD."
	REVISION "201103080000Z" -- March 08, 2011
		DESCRIPTION
		"Added/updated arrisRouterFWBlockHTTP, arrisRouterFWBlockP2P, arrisRouterFWBlockIdent, arrisRouterFWBlockICMP, arrisRouterFWBlockMulticast, arrisRouterFWSecurityLevel, arrisRouterFWResetDefaults and arrisRouterLanCustomComments."
	REVISION "201103070000Z" -- March 7, 2011
	       	DESCRIPTION
		"Added arrisRouterWanCurrentIpAddr and remove arrisRouterWanCurrentGW."
      REVISION "201103060000Z" -- March 06, 2011
        DESCRIPTION
        "Added arrisRouterFWVSSrcPortExclude, arrisRouterFWVSDestPortExclude, arrisRouterFWEnableWanSSH, and arrisRouterFWEnableWanSNMP."
      REVISION "201103050000Z" -- March 05, 2011
        DESCRIPTION
            "Added/updated arrisRouterFWBlockHTTP, arrisRouterFWBlockP2P, arrisRouterFWBlockIdent, arrisRouterFWBlockICMP and arrisRouterFWBlockMulticast."
      REVISION "201103030000Z" -- March 03, 2011
        DESCRIPTION
            "Removed size restrictions on string: arrisRouterLanCustomComments. Added: arrisRouterFWResetDefaults, arrisRouterFWBlockHTTP, arrisRouterFWBlockIdent, and arrisRouterFWBlockP2P."
      REVISION "201103020000Z" -- March 02, 2011
        DESCRIPTION
            "Added arrisRouterXmlProvisioningFile and arrisRouterXmlProvisioningStatus and arrisRouterWiFiCustomSSIDStr
	    Added arrisRouterWanCurrentGW and arrisRouterWanDHCPExpire."
	  REVISION "201102090000Z" -- February 09, 2011
		DESCRIPTION
		"Added arrisRouterSNTPServerStatus from remove list"
      REVISION "201102040000Z" -- February 04, 2011
        DESCRIPTION
		"Added arrisRouterLanOverrideDNS."
      REVISION "201101180000Z" -- January 18, 2011
        DESCRIPTION
		"Added arrisRouterWiFiEnableRadioNow."
      REVISION "201101100000Z" -- January 10, 2011
        DESCRIPTION
        "Changed arrisRouterWEP64BitKeyValue and arrisRouterWEP128BitKeyValue from OCTET STRING to DisplayString. Removed size limits."
      REVISION "201101090000Z" -- January 09, 2011
        DESCRIPTION
		"Added arrisRouterRIPRoutedSubnetDHCP and arrisRouterRIPRoutedSubnetNAT."
      REVISION "201101070000Z" -- January 7, 2011
         DESCRIPTION
	"Added arrisRouterWMMAPSD MIB."
      REVISION "201012240000Z" -- December 24, 2010
         DESCRIPTION
	"Updated arrisRouterLanPassThru description."
      REVISION "201012220000Z" -- December 22, 2010
	DESCRIPTION
		"Added 8-bit limitation to arrisRouterRIPAuthKeyID"
      REVISION "201012170000Z" -- December 17, 2010
		DESCRIPTION
		"Added arrisRouterRIPSendCMInterface,
		arrisRouterRIPRoutedSubnetIP,arrisRouterRIPRoutedSubnetGWNetIPType,
		arrisRouterRIPRoutedSubnetGWNetIP,arrisRouterRIPRoutedSubnetMask,
		arrisRouterRIPRoutedSubnetEnabled,arrisRouterRIPSendCMInterface"
	REVISION "201012150000Z" -- December 15, 2010
        DESCRIPTION
		"Added 'auto' option to arrisRouterWiFiGuardInterval
		and arrisRouterWanCurrentNetMask, arrisRouterWanIFMacAddr
		arrisRouterEnableParentalCont, arrisRouterDebugLogTable
		and Sercomm merge MIB 20101202"

      REVISION "201012140000Z" -- December 14, 2010
        DESCRIPTION
        "Added arrisRouterRIPSendCMInterface."
      REVISION "201012100000Z" -- December 10, 2010
        DESCRIPTION
        "Added arrisRouterRIPRoutedSubnetIPType, arrisRouterRIPRoutedSubnetIP, arrisRouterRIPRoutedSubnetGWNetIPType,
        arrisRouterRIPRoutedSubnetGWNetIP, arrisRouterRIPRoutedSubnetMask, arrisRouterRIPRoutedSubnetEnabled."
      REVISION "201012060000Z" -- December 06, 2010
         DESCRIPTION
        "Made arrisRouterCurrentTime read-write."
      REVISION "201012040000Z" -- December 04, 2010
         DESCRIPTION
        "Changed the name arrisRouterRIPNetmask to arrisRouterRIPPrefixLen.  Fixed typo in arrisRouterMACAccessAddr."
      REVISION "201012020000Z" -- December 02, 2010
         DESCRIPTION
	  "Added 'auto' option to arrisRouterWiFiGuardInterval."
      REVISION "201011290000Z" -- November 29, 2010
         DESCRIPTION
	  "Sercomm merge MIB 20101126"
      REVISION "201011260000Z" -- November 26, 2010
         DESCRIPTION
	  "Added 20/40 option to arrisRouterWiFiChannelBW."
	  REVISION "201011230000Z" -- November 23, 2010
         DESCRIPTION
		"Reduce maximum length of arrisRouterRIPAuthKeyString to 16. Added wpaWpa2Psk(7) and wpaWpa2Enterprise(8) to arrisRouterBssSecurityMode."
	  REVISION "201011080000Z" -- November 08, 2010
         DESCRIPTION
		"Added arrisRouterWanCurrentNetMask column to arrisRouterWanCurrentTable to make it easier for IPv4 addresses to display netmask.
		Reduced number of WAN table entries from max of 8 to 4."
	  REVISION "201011010000Z" -- November 01, 2010
         DESCRIPTION
		"Added arrisRouterWanIFMacAddr."
	  REVISION "201010280000Z" -- October 28, 2010
         DESCRIPTION
		 "Fixed syntax error on arrisRouterLanCPEAging and other minor syntax warnings."
	  REVISION "201010270000Z" -- October 27, 2010
         DESCRIPTION
		"Removed unnecessary arrisRouterWanApplyLog, arrisRouterLanApplyLog, and arrisRouterFWApplyLog.
		Added arrisRouterDebugLogTable."
	  REVISION "201010250000Z" -- October 25, 2010
         DESCRIPTION
		"Added arrisRouterFWAllowICMP."
	  REVISION "201010210000Z" -- October 21, 2010
         DESCRIPTION
		"Added arrisRouterTACACSPort, arrisRouterTACACSAddr and arrisRouterTACACSSecretKey."
	  REVISION "201010200000Z" -- October 20, 2010
         DESCRIPTION
		"Added column: arrisRouterFWVirtSrvLocalPortStart and arrisRouterFWVirtSrvLocalPortEnd to the table: arrisRouterFWVirtSrvTable.
		This caused arrisRouterFWVirtSrvRowStatus to be renumbered from 9 to 11.
		Added arrisRouterLanCPEAging to arrisRouterLanSrvTable."
	  REVISION "201010150000Z" -- October 15, 2010
         DESCRIPTION
		"Enhanced arrisRouterFactoryDefaults and renamed to arrisRouterDefaults."
	  REVISION "201010120000Z" -- October 12, 2010
         DESCRIPTION
		"Modified values for arrisRouterLanPassThru.
		Renumbered items under arrisRouterSysCfg.
		Added arrisRouterCustomID.
		Added table: arrisRouterAuthTable.
		Added arrisRouterCurrentTime."
	  REVISION "201009300000Z" -- September 30, 2010
         DESCRIPTION
		"Added arrisRouterCustomId."
	  REVISION "201009240000Z" -- September 24, 2010
         DESCRIPTION
		"Added arrisRouterLanUPnPEnable and removed arrisRouterFWEnableUPnP."
	  REVISION "201009210000Z" -- September 21, 2010
         DESCRIPTION
			"Added arrisRouterClearLogs."
	  REVISION "201009160000Z" -- September 16, 2010
         DESCRIPTION
            "Modified values for arrisRouterLanSettings.
            Added arrisRouterAuthTable. Added arrisRouterFWL2TPPassThru.
            Modified values for arrisRouterRIPAuthEnable.  Renamed arrisRouterRIPAuthKey to arrisRouterRIPAuthKeyString.
            Added arrisRouterRIPAuthKeyChain.
			Added arrisRouterCustomSettings."
      REVISION "201009070000Z" -- September 07, 2010
         DESCRIPTION
	"Added arrisRouterWiFiResetDefaults."
      REVISION "201009010000Z" -- September 01, 2010
         DESCRIPTION
				"Added arrisRouterWiFiResetDefaults."
      REVISION "201008170000Z" -- August 17, 2010
         DESCRIPTION
            "Further update to arrisRouterWiFiMode. Added arrisRouterLogLevel.
             Added arrisRouterWpsResultStatus and renumbered other OIDs under arrisRouterWPSCfg.
             Updated definition for arrisRouterWpsStatus.
             Added Ethernet table: arrisRouterLanEtherPortTable."
      REVISION "201008110000Z" -- Auguest 11, 2010
      	 DESCRIPTION
      	"Added arrisRouterLanClientAdapterType."
      REVISION "201007280000Z" -- July 28, 2010
      	 DESCRIPTION
      	"Updated base on arris 20100727."
      REVISION "201007230000Z" -- July 23, 2010
         DESCRIPTION
		"Added arrisRouterSerialNumber, arrisRouterBootCodeVersion, arrisRouterHardwareVersion, arrisRouterFirmwareVersion."
      REVISION "201007220000Z" -- July 22, 2010
         DESCRIPTION
            "Updated values for arrisRouterWpsPushButton.  Added arrisRouterWpsStatus.
            Update values for arrisRouterWiFiMode.
			Removed arrisRouterWpsConfigReg."
      REVISION "201007140000Z" -- July 14, 2010
         DESCRIPTION
            "Added numeric index to arrisRouterLanCustomTable."
      REVISION "201007120000Z" -- July 12, 2010
         DESCRIPTION
            "Added arrisRouterWebAccessSetting."

      REVISION "201007200000Z" -- July 20, 2010
      	 DESCRIPTION
      "Base on arris 20100630, update Comcast MIB."
      REVISION "201006300000Z" -- June 30, 2010
         DESCRIPTION
            "Reduced size of arrisRouterTraceRtLog to 255.  Changed minimum value of arrisRouterWiFiBeaconInterval to 1."
      REVISION "201006280000Z" -- June 28, 2010
         DESCRIPTION
            "Changed arrisRouterWiFiEnableRadio back to TruthValue -- typo fixed.  Made arrisRouterLanCustomIPAddr and arrisRouterLanCustomIPAddrType writable."
      REVISION "201006200000Z" -- June 20, 2010
         DESCRIPTION
                "Removed arrisRouterLanDNSTableFreeIdx and renumbered items below it."
      REVISION "201006170000Z" -- June 17, 2010
         DESCRIPTION
            "Changed arrisRouterFWVirtSrvTable to use row status: add arrisRouterFWVirtSrvRowStatus and remove arrisRouterFWVirtSrvEnabled.
            Changed arrisRouterFWIPFilterTable to use row status: add arrisRouterFWIPFilterRowStatus and remove arrisRouterFWIPFilterEnabled.
            Changed arrisRouterFWMACFilterTable to use row status: add arrisRouterFWMACFilterRowStatus.
            Change arrisRouterFWPortTrigTable to use row status: add arrisRouterFWPortTrigRowStatus and remove arrisRouterFWPortTrigEnabled.
            Added arrisRouterLanPassThru to Lan interface.
            Added arrisRouterLanFirewallOn to Lan interface."
      REVISION "201005270000Z" -- May 27, 2010
         DESCRIPTION
            "Added arrisRouterLanGatewayIp2 and arrisRouterLanGatewayIp2Type to handle simultaneous IPv4 and IPv6 on LAN.
            Added resetDefaults to arrisRouterFWApplySettings.  Added arrisRouterName.  Added arrisRouterFWAllowAll.
            Added restartWLAN to arrisRouterLanSettings."
      REVISION "201005260000Z" -- May 26, 2010
         DESCRIPTION
             "Added arrisRouterFWSecurityLevel and arrisRouterLanIPv6Mode and added arrisRouterLanCustomComments.  Put size ranges on most objects of type DisplayString."
      REVISION "201005110000Z" -- May 11, 2010
         DESCRIPTION
             "Removed unnecessary enable 'firewall' and 'parental controls' logs.  These are always 'on'.  They can be configured to email or not.
			 Removed arrisHostAccessHttpWan which duplicates functionality of arrisRouterFWEnableRemoteMgmt."
      REVISION "201005070000Z" -- May 7, 2010
         DESCRIPTION
             "Added variables to obtain lowest 'available' index for tables that have the ability via RowStatus to create new rows."
      REVISION "201005030000Z" -- May 3, 2010
         DESCRIPTION
             "Added user and MSO change log tables.  Added arrisRouterLanCustomTable for 'friendly name' and other attributes.  Enhanced arrisRouterClientsUpDownTable."
      REVISION "201004290000Z" -- April 29, 2010
         DESCRIPTION
             "Removed unnecessary DST variable.  Added firewall and parental control log tables. Added web access table.  Removed unnecessary log config variables."
      REVISION "201004270000Z" -- April 27, 2010
         DESCRIPTION
             "Merged WAN static/dynamic for simplicity.  Added global 'Apply settings'.  Added 'time-of-day' to firewall and parental control rules. Remove WMM VLAN -- not needed."
      REVISION "201004250000Z" -- April 25, 2010
         DESCRIPTION
             "Updated Wan config to handle multiple IP addresses and separate out static vs. dynamic."
      REVISION "201004220000Z" -- April 22, 2010
         DESCRIPTION
             "Added 'apply log', made RIP settings 'global' and removed UPnP Lan tables, and update Wan config to handle multiple IP addresses."
      REVISION "201002110000Z" -- February 11, 2010
         DESCRIPTION
             "Initial Revision."
::= { arrisProdIdRouter 1 }

arrisRouterMibObjects			 OBJECT IDENTIFIER ::= { arrisRouterMib 1 }
arrisRouterWanConfig			 OBJECT IDENTIFIER ::= { arrisRouterMibObjects 1 }
arrisRouterLanConfig			 OBJECT IDENTIFIER ::= { arrisRouterMibObjects 2 }
arrisRouterWirelessCfg			 OBJECT IDENTIFIER ::= { arrisRouterMibObjects 3 }
arrisRouterFWCfg				 OBJECT IDENTIFIER ::= { arrisRouterMibObjects 4 }
arrisRouterSysCfg				 OBJECT IDENTIFIER ::= { arrisRouterMibObjects 5 }
arrisRouterHostAccess			 OBJECT IDENTIFIER ::= { arrisRouterMibObjects 6 }
arrisRouterPingMgmt				 OBJECT IDENTIFIER ::= { arrisRouterMibObjects 7 }
arrisRouterTraceRtMgmt			 OBJECT IDENTIFIER ::= { arrisRouterMibObjects 8 }
arrisRouterICtrl                 OBJECT IDENTIFIER ::= { arrisRouterMibObjects 10 }

arrisRouterApplyAllSettings OBJECT-TYPE
     SYNTAX      INTEGER { unknown(0), applySettings(1) }
     MAX-ACCESS  read-write
     STATUS      current
     DESCRIPTION "This applies settings for the entire MIB.  All services and components in the router will be restarted."
     ::= { arrisRouterMibObjects 9 }

arrisRouterWanConnType OBJECT-TYPE
     SYNTAX      INTEGER { unknown(0), dynamic(1), static(2), l2tpStatic(5), l2tpDynamic(6) }
     MAX-ACCESS  read-write
     STATUS      current
     DESCRIPTION "The type of Wan connection."
     ::= { arrisRouterWanConfig 1 }

arrisRouterWanConnHostName OBJECT-TYPE
     SYNTAX      DisplayString (SIZE (0..128))
     MAX-ACCESS  read-write
     STATUS      current
     DESCRIPTION "The host name."
     ::= { arrisRouterWanConfig 2 }

arrisRouterWanConnDomainName OBJECT-TYPE
     SYNTAX      DisplayString (SIZE (0..128))
     MAX-ACCESS  read-write
     STATUS      current
     DESCRIPTION "The domain name."
     ::= { arrisRouterWanConfig 3 }

arrisRouterWanMTUSize OBJECT-TYPE
     SYNTAX      Unsigned32 (256..1500)
     MAX-ACCESS  read-write
     STATUS      current
     DESCRIPTION "The MTU size for the Wan connection.  Specify 0 for auto-set."
     ::= { arrisRouterWanConfig 4 }

arrisRouterWanApply OBJECT-TYPE
     SYNTAX      INTEGER { noApply(0), apply(1) }
     MAX-ACCESS  read-write
     STATUS      current
     DESCRIPTION "Set to apply(1) to set all Wan settings."
     ::= { arrisRouterWanConfig 5 }

arrisRouterWanCurrentTable OBJECT-TYPE
      SYNTAX      SEQUENCE OF ArrisRouterWanCurrentEntry
      MAX-ACCESS  not-accessible
      STATUS      current
      DESCRIPTION "Table contains information for a specific Static Wan IP address.  In some environments, there may be both an IPv6 and IPv6 address or multiple IPv6 addresses."
      ::= { arrisRouterWanConfig 7 }

arrisRouterWanCurrentEntry OBJECT-TYPE
      SYNTAX      ArrisRouterWanCurrentEntry
      MAX-ACCESS  not-accessible
      STATUS      current
      DESCRIPTION "Table contains information for a specific Static Wan IP address.  In some environments, there may be both an IPv6 and IPv6 address or multiple IPv6 addresses."
      INDEX { arrisRouterWanCurrentIPIndex }
      ::= { arrisRouterWanCurrentTable 1 }

ArrisRouterWanCurrentEntry ::= SEQUENCE {
        arrisRouterWanCurrentIPIndex		    Unsigned32,
        arrisRouterWanCurrentIPAddrType		    InetAddressType,
        arrisRouterWanCurrentIPAddr 		    InetAddress,
        arrisRouterWanCurrentPrefix 		    InetAddressPrefixLength,
        arrisRouterWanCurrentGWType		    InetAddressType,
        arrisRouterWanCurrentGW                     InetAddress,
        arrisRouterWanCurrentIPType                 INTEGER,
        arrisRouterWanCurrentNetMask                InetAddress,
        arrisRouterWanCurrentPrefixDelegationV6     InetAddressIPv6,
        arrisRouterWanCurrentPrefixDelegationV6Len  InetAddressPrefixLength,
        arrisRouterWanCurrentPreferredLifetimeV6    INTEGER,
        arrisRouterWanCurrentValidLifetimeV6        INTEGER
    }

arrisRouterWanCurrentIPIndex OBJECT-TYPE
     SYNTAX      Unsigned32
     MAX-ACCESS  not-accessible
     STATUS      current
     DESCRIPTION "Index currently limit to 4."
     ::= { arrisRouterWanCurrentEntry 1 }

arrisRouterWanCurrentIPAddrType OBJECT-TYPE
     SYNTAX      InetAddressType
     MAX-ACCESS  read-only
     STATUS      current
     DESCRIPTION "Static IP address type for Wan connection."
     ::= { arrisRouterWanCurrentEntry 2 }

arrisRouterWanCurrentIPAddr OBJECT-TYPE
     SYNTAX      InetAddress
     MAX-ACCESS  read-only
     STATUS      current
     DESCRIPTION "Static IP address for Wan connection."
     ::= { arrisRouterWanCurrentEntry 3 }

arrisRouterWanCurrentPrefix OBJECT-TYPE
     SYNTAX      InetAddressPrefixLength
     MAX-ACCESS  read-only
     STATUS      current
     DESCRIPTION "Netmask (prefix) for Wan connection."
     ::= { arrisRouterWanCurrentEntry 4 }

arrisRouterWanCurrentGWType OBJECT-TYPE
     SYNTAX      InetAddressType
     MAX-ACCESS  read-only
     STATUS      current
     DESCRIPTION "Gateway address type for Wan connection."
     ::= { arrisRouterWanCurrentEntry 5 }

arrisRouterWanCurrentGW OBJECT-TYPE
     SYNTAX      InetAddress
     MAX-ACCESS  read-only
     STATUS      current
     DESCRIPTION "Gateway address for Wan connection."
     ::= { arrisRouterWanCurrentEntry 6 }

arrisRouterWanCurrentIPType OBJECT-TYPE
     SYNTAX      INTEGER { unknown(0), dynamic(1), static(2) }
     MAX-ACCESS  read-only
     STATUS      current
     DESCRIPTION "Type of IP address."
     ::= { arrisRouterWanCurrentEntry 7 }

arrisRouterWanCurrentNetMask OBJECT-TYPE
     SYNTAX      InetAddress
     MAX-ACCESS  read-only
     STATUS      current
     DESCRIPTION "The netmask for the WAN connection if it is IPv4."
     ::= { arrisRouterWanCurrentEntry 8 }

arrisRouterWanCurrentPrefixDelegationV6 OBJECT-TYPE
     SYNTAX      InetAddressIPv6
     MAX-ACCESS  read-only
     STATUS      current
     DESCRIPTION "The prefix, or initial bits of the address, given to the router to delegate to its attached CPEs."
     ::= { arrisRouterWanCurrentEntry 9 }

arrisRouterWanCurrentPrefixDelegationV6Len OBJECT-TYPE
     SYNTAX      InetAddressPrefixLength
     MAX-ACCESS  read-only
     STATUS      current
     DESCRIPTION "The length for the prefix to be delegated to attached CPEs."
     ::= { arrisRouterWanCurrentEntry 10 }

arrisRouterWanCurrentPreferredLifetimeV6 OBJECT-TYPE
     SYNTAX      INTEGER
     MAX-ACCESS  read-only
     STATUS      current
     DESCRIPTION "The preferred lifetime for the assigned IPv6 address of the router."
     ::= { arrisRouterWanCurrentEntry 11 }

arrisRouterWanCurrentValidLifetimeV6 OBJECT-TYPE
     SYNTAX      INTEGER
     MAX-ACCESS  read-only
     STATUS      current
     DESCRIPTION "The valid lifetime for the assigned IPv6 address of the router."
     ::= { arrisRouterWanCurrentEntry 12 }

-- arrsiRouterWannCurrentEntry End



arrisRouterWanStaticFreeIdx OBJECT-TYPE
     SYNTAX      Unsigned32 (0..4)
     MAX-ACCESS  read-only
     STATUS      current
     DESCRIPTION "The lowest available index which can be used to create a new row/instance in arrisRouterWanStaticTable.  A valid index is in the range [1..4].
                 If zero (0) is returned there are now more available rows."
     ::= { arrisRouterWanConfig 8 }

--Note currently only 1 static address is supported
arrisRouterWanStaticTable OBJECT-TYPE
      SYNTAX      SEQUENCE OF ArrisRouterWanStaticEntry
      MAX-ACCESS  not-accessible
      STATUS      current
      DESCRIPTION "Table contains information for a specific Static Wan IP address.  In some environments, there may be both an IPv6 and IPv6 address or multiple IPv6 addresses."
      ::= { arrisRouterWanConfig 9 }

arrisRouterWanStaticEntry OBJECT-TYPE
      SYNTAX      ArrisRouterWanStaticEntry
      MAX-ACCESS  not-accessible
      STATUS      current
      DESCRIPTION "Table contains information for a specific Static Wan IP address.  In some environments, there may be both an IPv6 and IPv6 address or multiple IPv6 addresses."
      INDEX { arrisRouterWanStaticIPIndex }
      ::= { arrisRouterWanStaticTable 1 }

ArrisRouterWanStaticEntry ::= SEQUENCE {
        arrisRouterWanStaticIPIndex			Unsigned32,
        arrisRouterWanStaticIPAddrType		InetAddressType,
        arrisRouterWanStaticIPAddr 			InetAddress,
        arrisRouterWanStaticPrefix 			InetAddressPrefixLength,
        arrisRouterWanStaticGatewayType		InetAddressType,
        arrisRouterWanStaticGateway			InetAddress,
        arrisRouterWanStaticRowStatus		RowStatus,
        arrisRouterWanDelegatedPrefixLength InetAddressPrefixLength,
        arrisRouterWanDelegatedPrefix InetAddressIPv6
    }

arrisRouterWanStaticIPIndex OBJECT-TYPE
     SYNTAX      Unsigned32
     MAX-ACCESS  not-accessible
     STATUS      current
     DESCRIPTION "Index currently limit to 4."
     ::= { arrisRouterWanStaticEntry 1 }

arrisRouterWanStaticIPAddrType OBJECT-TYPE
     SYNTAX      InetAddressType
     MAX-ACCESS  read-create
     STATUS      current
     DESCRIPTION "Static IP address type for Wan connection."
     ::= { arrisRouterWanStaticEntry 2 }

arrisRouterWanStaticIPAddr OBJECT-TYPE
     SYNTAX      InetAddress
     MAX-ACCESS  read-create
     STATUS      current
     DESCRIPTION "Static IP address for Wan connection."
     ::= { arrisRouterWanStaticEntry 3 }

arrisRouterWanStaticPrefix OBJECT-TYPE
     SYNTAX      InetAddressPrefixLength
     MAX-ACCESS  read-create
     STATUS      current
     DESCRIPTION "Netmask (prefix) for Wan connection."
     ::= { arrisRouterWanStaticEntry 4 }

arrisRouterWanStaticGatewayType OBJECT-TYPE
     SYNTAX      InetAddressType
     MAX-ACCESS  read-create
     STATUS      current
     DESCRIPTION "Gateway address type for Wan connection."
     ::= { arrisRouterWanStaticEntry 5 }

arrisRouterWanStaticGateway OBJECT-TYPE
     SYNTAX      InetAddress
     MAX-ACCESS  read-create
     STATUS      current
     DESCRIPTION "Gateway address for Wan connection."
     ::= { arrisRouterWanStaticEntry 6 }

arrisRouterWanStaticRowStatus OBJECT-TYPE
     SYNTAX      RowStatus
     MAX-ACCESS  read-create
     STATUS      current
     DESCRIPTION "RowStatus used to add/remove rows from the table."
     ::= { arrisRouterWanStaticEntry 7  }


arrisRouterWanDelegatedPrefixLength OBJECT-TYPE
     SYNTAX      InetAddressPrefixLength
     MAX-ACCESS  read-create
     STATUS      current
     DESCRIPTION "Length of IPV6 delegated prefix."
     ::= { arrisRouterWanStaticEntry 8 }

arrisRouterWanDelegatedPrefix OBJECT-TYPE
     SYNTAX      InetAddressIPv6
     MAX-ACCESS  read-create
     STATUS      current
     DESCRIPTION "IPV6 delegated prefix."
     ::= { arrisRouterWanStaticEntry 9 }


arrisRouterWanTunnelObjects	OBJECT IDENTIFIER ::= { arrisRouterWanConfig 10 }

arrisRouterWanUserName OBJECT-TYPE
     SYNTAX      DisplayString (SIZE (0..64))
     MAX-ACCESS  read-write
     STATUS      current
     DESCRIPTION "Tunnel Wan connection login user name (L2TP)"
     ::= { arrisRouterWanTunnelObjects 1 }

arrisRouterWanPassword OBJECT-TYPE
     SYNTAX      DisplayString (SIZE (0..64))
     MAX-ACCESS  read-write
     STATUS      current
     DESCRIPTION "Tunnel Wan connection login password (L2TP)"
     ::= { arrisRouterWanTunnelObjects 2 }

arrisRouterWanEnableIdleTimeout OBJECT-TYPE
     SYNTAX      TruthValue
     MAX-ACCESS  read-write
     STATUS      current
     DESCRIPTION "Idle timeout enabled? (L2TP)"
     ::= { arrisRouterWanTunnelObjects 3 }

arrisRouterWanIdleTimeout OBJECT-TYPE
     SYNTAX      Unsigned32
     UNITS		 "seconds"
     MAX-ACCESS  read-write
     STATUS      current
     DESCRIPTION "Idle timeout value for tunnel connection (LLTP)"
     DEFVAL { 300 }
     ::= { arrisRouterWanTunnelObjects 4 }

arrisRouterWanTunnelAddrType OBJECT-TYPE
     SYNTAX      InetAddressType
     MAX-ACCESS  read-write
     STATUS      current
     DESCRIPTION "Address type of tunnel server. (L2TP)"
     ::= { arrisRouterWanTunnelObjects 5 }

arrisRouterWanTunnelAddr OBJECT-TYPE
     SYNTAX      InetAddress
     MAX-ACCESS  read-write
     STATUS      current
     DESCRIPTION "Address of tunnel server. (L2TP)  Either the IP address or the host name is required."
     ::= { arrisRouterWanTunnelObjects 6 }

arrisRouterWanTunnelHostName OBJECT-TYPE
     SYNTAX      DisplayString (SIZE (0..128))
     MAX-ACCESS  read-write
     STATUS      current
     DESCRIPTION "Hostname of the tunnel server. (L2TP) Either the IP address or the host name is required."
     ::= { arrisRouterWanTunnelObjects 7 }

arrisRouterWanEnableKeepAlive OBJECT-TYPE
     SYNTAX      TruthValue
     MAX-ACCESS  read-write
     STATUS      current
     DESCRIPTION "KeepAlive timeout enabled? (L2TP)"
     ::= { arrisRouterWanTunnelObjects 8 }

arrisRouterWanKeepAliveTimeout OBJECT-TYPE
     SYNTAX      Unsigned32
     UNITS		 "seconds"
     MAX-ACCESS  read-write
     STATUS      current
     DESCRIPTION "KeepAlive timeout value (L2TP)"
     DEFVAL { 30 }
     ::= { arrisRouterWanTunnelObjects 9 }

arrisRouterWanDNSObjects	OBJECT IDENTIFIER ::= { arrisRouterWanConfig 11 }

-- This isn't an option now it's either all dynamic or all static can't separate out DNS servers at this time
arrisRouterWanUseAutoDNS OBJECT-TYPE
     SYNTAX      TruthValue
     MAX-ACCESS  read-write
     STATUS      current
     DESCRIPTION "Use automatic DNS servers as specified by ISP and DHCP."
     ::= { arrisRouterWanDNSObjects 1 }

arrisRouterWanCurrentDNSTable OBJECT-TYPE
      SYNTAX      SEQUENCE OF ArrisRouterWanCurrentDNSEntry
      MAX-ACCESS  not-accessible
      STATUS      current
      DESCRIPTION "Table contains the IP addresses of the current DNS servers. These may be dynamically obtained from the WAN DHCP server or these may
                    have been statically configured in arrisRouterWanStaticDNSTable."
      ::= { arrisRouterWanDNSObjects 2 }

arrisRouterWanCurrentDNSEntry OBJECT-TYPE
      SYNTAX      ArrisRouterWanCurrentDNSEntry
      MAX-ACCESS  not-accessible
      STATUS      current
      DESCRIPTION "Table contains the IP addresses of the current DNS servers. These may be dynamically obtained from the WAN DHCP server or these may
                    have been statically configured in arrisRouterWanStaticDNSTable."
      INDEX { arrisRouterWanCurrentDNSIPIndex }
      ::= { arrisRouterWanCurrentDNSTable 1 }

ArrisRouterWanCurrentDNSEntry ::= SEQUENCE {
        arrisRouterWanCurrentDNSIPIndex			Unsigned32,
        arrisRouterWanCurrentDNSIPAddrType		InetAddressType,
        arrisRouterWanCurrentDNSIPAddr 			InetAddress
    }

arrisRouterWanCurrentDNSIPIndex OBJECT-TYPE
     SYNTAX      Unsigned32 (1..8)
     MAX-ACCESS  not-accessible
     STATUS      current
     DESCRIPTION "Index which also indicates the order/priority for DNS lookups.
                  NOTE: For TS7.x, this mib only supports (1..4)"
     ::= { arrisRouterWanCurrentDNSEntry 1 }

arrisRouterWanCurrentDNSIPAddrType OBJECT-TYPE
     SYNTAX      InetAddressType
     MAX-ACCESS  read-only
     STATUS      current
     DESCRIPTION "Type of the IP address of the DNS server."
     ::= { arrisRouterWanCurrentDNSEntry 2 }

arrisRouterWanCurrentDNSIPAddr OBJECT-TYPE
     SYNTAX      InetAddress
     MAX-ACCESS  read-only
     STATUS      current
     DESCRIPTION "The IP address of the DNS server."
     ::= { arrisRouterWanCurrentDNSEntry 3 }

arrisRouterWanStaticDNSFreeIdx OBJECT-TYPE
     SYNTAX      Unsigned32 (0..8)
     MAX-ACCESS  read-only
     STATUS      current
     DESCRIPTION "Returns the smallest available free index to add a row to the arrisRouterWanStaticDNSTable.
                  A valid index is in the range [1..8].
                  If zero (0) is returned there are now more available rows."
     ::= { arrisRouterWanDNSObjects 3 }

arrisRouterWanStaticDNSTable OBJECT-TYPE
      SYNTAX      SEQUENCE OF ArrisRouterWanStaticDNSEntry
      MAX-ACCESS  not-accessible
      STATUS      current
      DESCRIPTION "Table contains the IP addresses of the DNS servers that have been statically assigned.
                   This table may be empty if arrisRouterWanUseAutoDNS is set to true."
      ::= { arrisRouterWanDNSObjects 4 }

arrisRouterWanStaticDNSEntry OBJECT-TYPE
      SYNTAX      ArrisRouterWanStaticDNSEntry
      MAX-ACCESS  not-accessible
      STATUS      current
      DESCRIPTION "Table contains the IP addresses of the DNS servers that have been statically assigned.  This table may be empty if arrisRouterWanUseAutoDNS is set to true."
      INDEX { arrisRouterWanStaticDNSIPIndex }
      ::= { arrisRouterWanStaticDNSTable 1 }

ArrisRouterWanStaticDNSEntry ::= SEQUENCE {
        arrisRouterWanStaticDNSIPIndex			Unsigned32,
        arrisRouterWanStaticDNSIPAddrType		InetAddressType,
        arrisRouterWanStaticDNSIPAddr 			InetAddress,
        arrisRouterWanStaticDNSRowStatus		RowStatus
    }

arrisRouterWanStaticDNSIPIndex OBJECT-TYPE
     SYNTAX      Unsigned32 (1..8)
     MAX-ACCESS  not-accessible
     STATUS      current
     DESCRIPTION "Index which also indicates the order/priority for DNS lookups.  There is a limit of 8 rows."
     ::= { arrisRouterWanStaticDNSEntry 1 }

arrisRouterWanStaticDNSIPAddrType OBJECT-TYPE
     SYNTAX      InetAddressType
     MAX-ACCESS  read-create
     STATUS      current
     DESCRIPTION "Type of the IP address of the DNS server."
     ::= { arrisRouterWanStaticDNSEntry 2 }

arrisRouterWanStaticDNSIPAddr OBJECT-TYPE
     SYNTAX      InetAddress
     MAX-ACCESS  read-create
     STATUS      current
     DESCRIPTION "The IP address of the DNS server."
     ::= { arrisRouterWanStaticDNSEntry 3 }

arrisRouterWanStaticDNSRowStatus OBJECT-TYPE
     SYNTAX      RowStatus
     MAX-ACCESS  read-create
     STATUS      current
     DESCRIPTION "The rowstatus used to add and remove rows."
     ::= { arrisRouterWanStaticDNSEntry 4 }

arrisRouterWanDHCPObjects	OBJECT IDENTIFIER ::= { arrisRouterWanConfig 12 }

arrisRouterWanRenewLease OBJECT-TYPE
     SYNTAX      INTEGER { noApply(0), apply(1) }
     MAX-ACCESS  read-write
     STATUS      current
     DESCRIPTION "Set to apply(1) to renew the primary public Wan DHCP lease."
     ::= { arrisRouterWanDHCPObjects 1 }

arrisRouterWanReleaseLease OBJECT-TYPE
     SYNTAX      INTEGER { noApply(0), apply(1) }
     MAX-ACCESS  read-write
     STATUS      current
     DESCRIPTION "Set to apply(1) to release the primary public Wan DHCP lease."
     ::= { arrisRouterWanDHCPObjects 2 }

arrisRouterWanDHCPDuration OBJECT-TYPE
     SYNTAX      Unsigned32
     UNITS		 "seconds"
     MAX-ACCESS  read-only
     STATUS      current
      DESCRIPTION "The number of seconds that the current Wan DHCP lease is valid."
     ::= { arrisRouterWanDHCPObjects 3 }

arrisRouterWanDHCPExpire OBJECT-TYPE
     SYNTAX      DateAndTime
     MAX-ACCESS  read-only
     STATUS      current
     DESCRIPTION "The date and time when the current Wan DHCP lease expires."
     ::= { arrisRouterWanDHCPObjects 4 }

arrisRouterWanRenewLeaseV6 OBJECT-TYPE
     SYNTAX      INTEGER { noApply(0), apply(1) }
     MAX-ACCESS  read-write
     STATUS      current
     DESCRIPTION "IPV6 Set to apply(1) to renew the primary public Wan DHCP lease."
     ::= { arrisRouterWanDHCPObjects 5 }

arrisRouterWanReleaseLeaseV6 OBJECT-TYPE
     SYNTAX      INTEGER { noApply(0), apply(1) }
     MAX-ACCESS  read-write
     STATUS      current
     DESCRIPTION "IPV6 Set to apply(1) to release the primary public Wan DHCP lease."
     ::= { arrisRouterWanDHCPObjects 6 }

arrisRouterWanDHCPDurationV6 OBJECT-TYPE
     SYNTAX      Unsigned32
     UNITS		 "seconds"
     MAX-ACCESS  read-only
     STATUS      current
      DESCRIPTION "IPV6 The number of seconds that the current Wan DHCP lease is valid."
     ::= { arrisRouterWanDHCPObjects 7 }

arrisRouterWanDHCPExpireV6 OBJECT-TYPE
     SYNTAX      DateAndTime
     MAX-ACCESS  read-only
     STATUS      current
     DESCRIPTION "IPV6 The date and time when the current Wan DHCP lease expires."
     ::= { arrisRouterWanDHCPObjects 8 }


arrisRouterWanDhcpSrvIPAddr OBJECT-TYPE
     SYNTAX      InetAddress
     MAX-ACCESS  read-only
     STATUS      current
     DESCRIPTION "The IP address of the DHCP server."
     ::= { arrisRouterWanDHCPObjects 9 }

arrisRouterWanDhcpOpt43Sub02 OBJECT-TYPE
     SYNTAX      INTEGER { erouter(0), ecm(1) }
     MAX-ACCESS  read-write
     STATUS      current
     DESCRIPTION "DHCP Option 43 Sub-option 2 content.
     When set the value to 'erouter(0)', the Option 43 Sub-option 2 content will be 'EROUTER' at the DHCPDISCOVER packet;
     When set the value to 'ecm(1)', the Option 43 Sub-option 2 content will be 'ECM' at the DHCPDISCOVER packet;"
     DEFVAL  { 0 }
     ::= { arrisRouterWanDHCPObjects 10 }

arrisRouterWanDHCPDUIDV6 OBJECT-TYPE
	SYNTAX      DisplayString (SIZE (0..130))
	MAX-ACCESS  read-only
	STATUS      current
	DESCRIPTION "The DHCP Unique ID (DUID) of the WAN DHCP Client."
	::= { arrisRouterWanDHCPObjects 11 }

arrisRouterWanDHCPSrvAddrV6 OBJECT-TYPE
	SYNTAX      InetAddressIPv6
	MAX-ACCESS  read-only
	STATUS      current
	DESCRIPTION "The IPv6 address of the accepted DHCPv6 server."
	::= { arrisRouterWanDHCPObjects 12 }

arrisRouterWanDHCPSrvDUIDV6 OBJECT-TYPE
	SYNTAX      DisplayString (SIZE (0..130))
	MAX-ACCESS  read-only
	STATUS      current
	DESCRIPTION "The DHCP Unique ID (DUID) of the accepted DHCPv6 server."
	::= { arrisRouterWanDHCPObjects 13 }

arrisRouterWanDHCPOpt61Ctl OBJECT-TYPE
     SYNTAX      INTEGER { disable(0), enable(1) }
     MAX-ACCESS  read-write
     STATUS      current
     DESCRIPTION "Set to enable(1) to enable option61 (RFC4361) instead of default (RFC2132)."
     ::= { arrisRouterWanDHCPObjects 14 }

arrisRouterWanIFMacAddr OBJECT-TYPE
     SYNTAX      MacAddress
     MAX-ACCESS  read-only
     STATUS      current
     DESCRIPTION "The MAC address of the WAN interface."
     ::= { arrisRouterWanConfig 13 }

arrisRouterWanInterface OBJECT-TYPE
     SYNTAX      INTEGER { unknown(0), cm(1), ether1(2), ether2(3), ether3(4), ether4(5), usb(7),cmNoReboot(11), ether1NoReboot(12) }
     MAX-ACCESS  read-write
     STATUS      current
     DESCRIPTION "The interface to use for WAN connectivity.  This only applies to Media Gateway products.
                Static routes should be configured to route traffic appropriately.  For the Arris Media Gateway product, configure the routes via the eSTB
                SNMP agent (or the configuration file) and use the standard MIB: InetCidrRouteTable."
     DEFVAL { cm }
     ::= { arrisRouterWanConfig 14 }

arrisRouterPrivateWanObjects   OBJECT IDENTIFIER ::= { arrisRouterWanConfig 15 }

arrisRouterPrivateWanRenewLease OBJECT-TYPE
     SYNTAX      INTEGER { noApply(0), apply(1) }
     MAX-ACCESS  read-write
     STATUS      current
     DESCRIPTION "Set to apply(1) to renew the primary Private Wan DHCP lease."
     ::= { arrisRouterPrivateWanObjects 1 }

arrisRouterPrivateWanReleaseLease OBJECT-TYPE
     SYNTAX      INTEGER { noApply(0), apply(1) }
     MAX-ACCESS  read-write
     STATUS      current
     DESCRIPTION "Set to apply(1) to release the primary Private Wan DHCP lease."
     ::= { arrisRouterPrivateWanObjects 2 }

arrisRouterPrivateWanDHCPDuration OBJECT-TYPE
     SYNTAX      Unsigned32
     UNITS		 "seconds"
     MAX-ACCESS  read-only
     STATUS      current
      DESCRIPTION "The number of seconds that the current Private Wan DHCP lease is valid."
     ::= { arrisRouterPrivateWanObjects 3 }

arrisRouterPrivateWanDHCPExpire OBJECT-TYPE
     SYNTAX      DateAndTime
     MAX-ACCESS  read-only
     STATUS      current
     DESCRIPTION "The date and time when the current Private Wan DHCP lease expires."
     ::= { arrisRouterPrivateWanObjects 4 }

arrisRouterPrivateWanCurrentIPAddrType OBJECT-TYPE
     SYNTAX      InetAddressType
     MAX-ACCESS  read-only
     STATUS      current
     DESCRIPTION "IP address type for Private WAN connection."
     ::= { arrisRouterPrivateWanObjects 5 }

arrisRouterPrivateWanCurrentIPAddr OBJECT-TYPE
     SYNTAX      InetAddress
     MAX-ACCESS  read-only
     STATUS      current
     DESCRIPTION "IP address for Private WAN connection."
     ::= { arrisRouterPrivateWanObjects 6 }

arrisRouterPrivateWanCurrentPrefix OBJECT-TYPE
     SYNTAX      InetAddressPrefixLength
     MAX-ACCESS  read-only
     STATUS      current
     DESCRIPTION "Netmask (prefix) for Private WAN connection."
     ::= { arrisRouterPrivateWanObjects 7 }

arrisRouterPrivateWanCurrentGWType OBJECT-TYPE
     SYNTAX      InetAddressType
     MAX-ACCESS  read-only
     STATUS      current
     DESCRIPTION "Gateway address type for Private WAN connection."
     ::= { arrisRouterPrivateWanObjects 8 }

arrisRouterPrivateWanCurrentGW OBJECT-TYPE
     SYNTAX      InetAddress
     MAX-ACCESS  read-only
     STATUS      current
     DESCRIPTION "Gateway address for Private WAN connection."
     ::= { arrisRouterPrivateWanObjects 9 }

arrisRouterPrivateWanCurrentNetMask OBJECT-TYPE
     SYNTAX      InetAddress
     MAX-ACCESS  read-only
     STATUS      current
     DESCRIPTION "The netmask for the private WAN connection if it is IPv4."
     ::= { arrisRouterPrivateWanObjects 10 }

arrisRouterPrivateWanCurrentDomainName OBJECT-TYPE
     SYNTAX      DisplayString
     MAX-ACCESS  read-only
     STATUS      current
     DESCRIPTION "The domain name for the private WAN connection."
     ::= { arrisRouterPrivateWanObjects 11 }

arrisRouterPrivateWanInterfaceName OBJECT-TYPE
     SYNTAX      DisplayString
     MAX-ACCESS  read-only
     STATUS      current
     DESCRIPTION "The interface name for the private WAN connection, i.e. bcm3"
     ::= { arrisRouterPrivateWanObjects 12 }

arrisRouterPrivateWanMacAddr OBJECT-TYPE
     SYNTAX      MacAddress
     MAX-ACCESS  read-only
     STATUS      current
     DESCRIPTION "The MAC address of the private WAN connection."
     ::= { arrisRouterPrivateWanObjects 13 }

arrisRouterPrivateWanCurrentDNSTable OBJECT-TYPE
      SYNTAX      SEQUENCE OF ArrisRouterPrivateWanCurrentDNSEntry
      MAX-ACCESS  not-accessible
      STATUS      current
      DESCRIPTION "Table contains the IP addresses of the current DNS servers."
      ::= { arrisRouterPrivateWanObjects 14 }

arrisRouterPrivateWanCurrentDNSEntry OBJECT-TYPE
      SYNTAX      ArrisRouterPrivateWanCurrentDNSEntry
      MAX-ACCESS  not-accessible
      STATUS      current
      DESCRIPTION "Table contains the IP addresses of the current DNS servers."
      INDEX { arrisRouterPrivateWanCurrentDNSIPIndex }
      ::= { arrisRouterPrivateWanCurrentDNSTable 1 }

ArrisRouterPrivateWanCurrentDNSEntry ::= SEQUENCE {
        arrisRouterPrivateWanCurrentDNSIPIndex			Unsigned32,
        arrisRouterPrivateWanCurrentDNSIPAddrType		InetAddressType,
        arrisRouterPrivateWanCurrentDNSIPAddr 			InetAddress
    }

arrisRouterPrivateWanCurrentDNSIPIndex OBJECT-TYPE
     SYNTAX      Unsigned32 (1..4)
     MAX-ACCESS  not-accessible
     STATUS      current
     DESCRIPTION "Index which also indicates the order/priority for DNS lookups."
     ::= { arrisRouterPrivateWanCurrentDNSEntry 1 }

arrisRouterPrivateWanCurrentDNSIPAddrType OBJECT-TYPE
     SYNTAX      InetAddressType
     MAX-ACCESS  read-only
     STATUS      current
     DESCRIPTION "Type of the IP address of the DNS server."
     ::= { arrisRouterPrivateWanCurrentDNSEntry 2 }

arrisRouterPrivateWanCurrentDNSIPAddr OBJECT-TYPE
     SYNTAX      InetAddress
     MAX-ACCESS  read-only
     STATUS      current
     DESCRIPTION "The IP address of the DNS server."
     ::= { arrisRouterPrivateWanCurrentDNSEntry 3 }

arrisRouterPrivateWanEnabled OBJECT-TYPE
     SYNTAX      TruthValue
     MAX-ACCESS  read-only
     STATUS      current
     DESCRIPTION "Returns true if the private WAN interface is enabled. "
     ::= { arrisRouterPrivateWanObjects 15 }

arrisRouterWanConnTypeV6 OBJECT-TYPE
     SYNTAX      INTEGER { unknown(0), dynamic(1), static(2) }
     MAX-ACCESS  read-write
     STATUS      current
     DESCRIPTION "IPV6 type of Wan connection."
     ::= { arrisRouterWanConfig 16 }

arrisRouterWanIPProvMode OBJECT-TYPE
     SYNTAX      INTEGER { disabledBridge(0), ipv4(1), ipv6(2), dualStack(3)}
     MAX-ACCESS  read-write
     STATUS      current
     DESCRIPTION "It controls the eRouter mode. When set the value to 'disabledBridge(0)', it will put the device into
                  full bridge mode(all the subnets become bridge mode) and turn off the WiFi radio. When set the value to ipv4(1)/ ipv6(2)/ dualStack(3),
                  it will put the device into corresponding router mode and turn on the WiFi radio."
     ::= { arrisRouterWanConfig 17 }


arrisRouterDSLiteWanObjects   OBJECT IDENTIFIER ::= { arrisRouterWanConfig 18 }

arrisRouterDSLiteWanEnable OBJECT-TYPE
     SYNTAX      TruthValue
     MAX-ACCESS  read-write
     STATUS      current
     DESCRIPTION "IPV6 Enable or disable the DSLite."
     DEFVAL { true }
     ::= { arrisRouterDSLiteWanObjects 1 }

arrisRouterDSLiteWanLSNATIPAddr OBJECT-TYPE
     SYNTAX      InetAddressIPv6
     MAX-ACCESS  read-write
     STATUS      deprecated
     DESCRIPTION "IPV6 The IP address of the LSNAT server."
     ::= { arrisRouterDSLiteWanObjects 2 }

arrisRouterDSLiteTcpMssClamping OBJECT-TYPE
     SYNTAX      TruthValue
     MAX-ACCESS  read-write
     STATUS      current
     DESCRIPTION "Turn on/off (TCP) MSS clamping for ipv6 tunnel."
     DEFVAL { true }
     ::= { arrisRouterDSLiteWanObjects 4 }

arrisRouterDSLiteTcpMssValue OBJECT-TYPE
     SYNTAX      Unsigned32
     MAX-ACCESS  read-write
     STATUS      current
     DESCRIPTION "TCP Mss value for ipv6 tunnel"
     ::= { arrisRouterDSLiteWanObjects 5 }

arrisRouterDSLiteWanResolvedAddr OBJECT-TYPE
     SYNTAX      InetAddressIPv6
     MAX-ACCESS  read-only
     STATUS      current
     DESCRIPTION "Resolved IPV6 address of the LSNAT server."
     ::= { arrisRouterDSLiteWanObjects 6 }

arrisRouterDSLiteWanLSNATAddrType OBJECT-TYPE
     SYNTAX      InetAddressType
     MAX-ACCESS  read-write
     STATUS      current
     DESCRIPTION "Address type of LSNAT. IPV6 or FQDN."
     ::= { arrisRouterDSLiteWanObjects 7 }

arrisRouterDSLiteWanLSNATAddr OBJECT-TYPE
     SYNTAX      OCTET STRING (SIZE (1..255))
     MAX-ACCESS  read-write
     STATUS      current
     DESCRIPTION "IPV6 The IP address of the LSNAT server."
     ::= { arrisRouterDSLiteWanObjects 8 }

arrisRouterDSLiteIPv6FragEnabled OBJECT-TYPE
     SYNTAX      TruthValue
     MAX-ACCESS  read-write
     STATUS      current
     DESCRIPTION "Enables or disable IPv6 fragmentation in DS-Lite."
     ::= { arrisRouterDSLiteWanObjects 9 }

arrisRouterDSLiteProvisioningStatus OBJECT-TYPE
     SYNTAX      TruthValue
     MAX-ACCESS  read-only
     STATUS      current
     DESCRIPTION "IPv6 DS-Lite provisioning status."
     ::= { arrisRouterDSLiteWanObjects 10 }

arrisRouterDSLiteOperationalStatus OBJECT-TYPE
     SYNTAX      TruthValue
     MAX-ACCESS  read-only
     STATUS      current
     DESCRIPTION "IPv6 DS-Lite Operational status."
     ::= { arrisRouterDSLiteWanObjects 11 }

arrisRouterSoftGreWanObjects   OBJECT IDENTIFIER ::= { arrisRouterWanConfig 19 }

arrisRouterSoftGreWanTable OBJECT-TYPE
     SYNTAX      SEQUENCE OF ArrisRouterSoftGreWanEntry
     MAX-ACCESS  not-accessible
     STATUS      current
     DESCRIPTION "Table contains information for a specific SoftGreWan."
     ::= { arrisRouterSoftGreWanObjects 1 }

arrisRouterSoftGreWanEntry OBJECT-TYPE
     SYNTAX      ArrisRouterSoftGreWanEntry
     MAX-ACCESS  not-accessible
     STATUS      current
     DESCRIPTION "Table contains information for a specific SoftGreWan.  ONLY Index of 1 currently Supported!"
     INDEX { ifIndex }	--from IF-MIB
     ::= { arrisRouterSoftGreWanTable 1 }

ArrisRouterSoftGreWanEntry ::= SEQUENCE {
     arrisRouterSoftGreWanEnable                  TruthValue,
     arrisRouterSoftGreMappedInterface            Unsigned32,
     arrisRouterSoftGreMaxSessions                INTEGER,
     arrisRouterSoftGreWanControllerFqdn          DisplayString,
     arrisRouterSoftGreWanControllerProvisionedSecondaryIpAddressType   InetAddressType,
     arrisRouterSoftGreWanControllerProvisionedSecondaryIpAddress   InetAddress,
     arrisRouterSoftGreWanFailoverPingCount       INTEGER,
     arrisRouterSoftGreWanFailoverPingInterval    INTEGER,
     arrisRouterSoftGreWanFailoverThreshold       INTEGER,
     arrisRouterSoftGreCircuitIdEnabled           TruthValue,
     arrisRouterSoftGreRemoteIdEnabled            TruthValue,
     arrisRouterSoftGreRadiusEnabled              TruthValue,
     arrisRouterSoftGreRadiusServerAddressType    InetAddressType,
     arrisRouterSoftGreRadiusServerAddress        InetAddress,
     arrisRouterSoftGreRadiusServerPort           Unsigned32,
     arrisRouterSoftGreRadiusKey                  DisplayString,
     arrisRouterSoftGreRadiusReAuthInterval       Unsigned32,
     arrisRouterSoftGreVlanQEnable                TruthValue,
     arrisRouterSoftGreWanDscp                    DscpOrAny,
     arrisRouterSoftGreWanDNSRetryTimer           Unsigned32,
     arrisRouterSoftGreWanCurrentControllerIPAddressType   InetAddressType,
     arrisRouterSoftGreWanCurrentControllerIPAddress       InetAddress,
     arrisRouterSoftGreWanPrimaryControllerIPAddressType   InetAddressType,
     arrisRouterSoftGreWanPrimaryControllerIPAddress       InetAddress,
     arrisRouterSoftGreWanSecondaryControllerIPAddressType InetAddressType,
     arrisRouterSoftGreWanSecondaryControllerIPAddress     InetAddress,
     arrisRouterSoftGreWanStatus                  INTEGER,
     arrisRouterSoftGreTransportInterface         INTEGER,
     arrisRouterSoftGreRadiusTransportInterface   INTEGER,
     arrisRouterSoftGreAcctServerAddressType      InetAddressType,
     arrisRouterSoftGreAcctServerAddress          InetAddress,
     arrisRouterSoftGreAcctServerPort             Unsigned32,
     arrisRouterSoftGreAcctKey                    DisplayString,
     arrisRouterSoftGreAcctInterval               Unsigned32,
     arrisRouterSoftGreRadiusSecondaryServerAddressType    InetAddressType,
     arrisRouterSoftGreRadiusSecondaryServerAddress        InetAddress,
     arrisRouterSoftGreRadiusSecondaryServerPort           Unsigned32,
     arrisRouterSoftGreRadiusSecondaryKey                  DisplayString,
     arrisRouterSoftGreRadiusSecondaryReAuthInterval       Unsigned32,
     arrisRouterSoftGreRemoteIdUseCMMac                    TruthValue,
     arrisRouterSoftGreRadiusAcctEnabled                   TruthValue,
     arrisRouterSoftGreWanFailurePingInterval              INTEGER,
     arrisRouterSoftGreMultiHotspotEnable                  TruthValue,
     arrisRouterSoftGreReconnectToPrimary                  INTEGER,
     arrisRouterSoftGreTunnelUpTime                        INTEGER,
     arrisRouterSoftGreWanActiveMonitoringTimer            INTEGER,
     arrisRouterSoftGreWanPassiveMonitoringTimer           INTEGER,
     arrisRouterSoftGreWanActiveMonitoringDhcpIpAddressFqdn DisplayString
}

arrisRouterSoftGreWanEnable OBJECT-TYPE
     SYNTAX      TruthValue
     MAX-ACCESS  read-write
     STATUS      current
     DESCRIPTION "Enable or disable the SoftGRE WiFi Hotspot Client."
     DEFVAL { false }
     ::= { arrisRouterSoftGreWanEntry 1 }

arrisRouterSoftGreMappedInterface OBJECT-TYPE
     SYNTAX      Unsigned32
     MAX-ACCESS  read-write
     STATUS      current
     DESCRIPTION "Name of the member physical network interface (or virtual
                  network interface in the case of a wireless SSID) comprising
                  the logical interface, aka LAN subnet.
                  This mib object takes in an unsigned integer with the
                  following bitmap setup:

                  0x00000001 // ethernet (unsupported)
                  0x00000002 // usb (unsupported)
                  0x00000004 // moca (unsupported)
                  0x00000008 // ssid0 (unsupported)
                  0x00000010 // ssid1 (unsupported)
                  0x00000020 // ssid2
                  0x00000040 // ssid3 (unsupported)
                  0x00000080 // ssid4 (unsupported)
                  0x00000100 // ssid5 (unsupported)
                  0x00000200 // ssid6 (unsupported)
                  0x00000400 // ssid7 (unsupported)
                  Example of mapping the ssid2 to the
                  SoftGre subnet: 0x00000020
                  Note that by assigning this interface to the SoftGre
                  Application causes it to be unusable for LAN services."
     ::= { arrisRouterSoftGreWanEntry 2 }

arrisRouterSoftGreMaxSessions OBJECT-TYPE
     SYNTAX      INTEGER
     MAX-ACCESS  read-write
     STATUS      current
     DESCRIPTION "The maximum  number of roaming devices for this AP
                  Setting the number of concurrent SoftGre client sessions to
                  0 must cause the following actions to be performed by
                  the Gateway.
                  Disable broadcast of SoftGre SSID (No clients can associate)
                  SoftGRE interface is disabled (No routing possible)
                  Release the public IP associated to the SoftGRE interface"
     DEFVAL  { 5 }
     ::= { arrisRouterSoftGreWanEntry 3 }

arrisRouterSoftGreWanControllerFqdn OBJECT-TYPE
    SYNTAX      DisplayString (SIZE(0..255))
    MAX-ACCESS  read-write
    STATUS      current
    DESCRIPTION "The FQDN of the WLAN GW that will terminate tunnels from this AP."
     ::= { arrisRouterSoftGreWanEntry 4 }

arrisRouterSoftGreWanControllerProvisionedSecondaryIpAddressType OBJECT-TYPE
    SYNTAX      InetAddressType
    MAX-ACCESS  read-write
    STATUS      current
    DESCRIPTION
        "The type of internet address used for the secondary WLAN GW that will terminate tunnels from this AP."
    ::= { arrisRouterSoftGreWanEntry 5 }

arrisRouterSoftGreWanControllerProvisionedSecondaryIpAddress OBJECT-TYPE
    SYNTAX      InetAddress
    MAX-ACCESS  read-write
    STATUS      current
    DESCRIPTION "The IP address of the secondary WLAN GW that will terminate tunnels from this AP.
    If the arrisRouterSoftGreWanControllerFqdn is FQDN format, this value will be ignored.
    When the MIB arrisRouterSoftGreWanControllerProvisionedSecondaryIpAddress is valid, the value of arrisRouterSoftGreWanControllerProvisionedSecondaryIpAddress
    will also be ignored if the AddressType of arrisRouterSoftGreWanControllerProvisionedSecondaryIpAddressType is different from the AddressType of arrisRouterSoftGreWanControllerFqdn."
     ::= { arrisRouterSoftGreWanEntry 6 }

arrisRouterSoftGreWanFailoverPingCount OBJECT-TYPE
     SYNTAX      INTEGER
     MAX-ACCESS  read-write
     STATUS      current
     DESCRIPTION "Number of ICMP Pings sent at a regular interval for WLAN GW
                  reachability health check"
     DEFVAL  { 3 }
     ::= { arrisRouterSoftGreWanEntry 7 }

arrisRouterSoftGreWanFailoverPingInterval OBJECT-TYPE
     SYNTAX      INTEGER
     MAX-ACCESS  read-write
     STATUS      current
     DESCRIPTION "Configured interval in seconds between WLAN GW reachability health checks"
     DEFVAL  { 60 }
     ::= { arrisRouterSoftGreWanEntry 8 }

arrisRouterSoftGreWanFailoverThreshold OBJECT-TYPE
     SYNTAX      INTEGER
     MAX-ACCESS  read-write
     STATUS      current
     DESCRIPTION "Number of consecutive un-acknowledged pings before it is determined
                  that the current WLAN GW is no longer available and will fail-over
                  to another WLAN GW if the DNS responded with more than one WLAN GW IP"
     DEFVAL  { 3 }
     ::= { arrisRouterSoftGreWanEntry 9 }

arrisRouterSoftGreCircuitIdEnabled OBJECT-TYPE
     SYNTAX      TruthValue
     MAX-ACCESS  read-write
     STATUS      current
     DESCRIPTION "Enable or disable the SoftGRE Circuit ID being added to DHCP"
     DEFVAL { true }
     ::= { arrisRouterSoftGreWanEntry 10 }

arrisRouterSoftGreRemoteIdEnabled OBJECT-TYPE
     SYNTAX      TruthValue
     MAX-ACCESS  read-write
     STATUS      current
     DESCRIPTION "Enable or disable the SoftGRE RemoteId being added to DHCP"
     DEFVAL { true }
     ::= { arrisRouterSoftGreWanEntry 11 }

arrisRouterSoftGreRadiusEnabled OBJECT-TYPE
     SYNTAX      TruthValue
     MAX-ACCESS  read-write
     STATUS      current
     DESCRIPTION "Enable or disable Radius Authentication for the SoftGRE Tunnel"
     DEFVAL { false }
     ::= { arrisRouterSoftGreWanEntry 12 }

arrisRouterSoftGreRadiusServerAddressType OBJECT-TYPE
    SYNTAX      InetAddressType
    MAX-ACCESS  read-write
    STATUS      current
    DESCRIPTION
        "The type of internet address used for arrisRouterRadiusAddress."
    ::= { arrisRouterSoftGreWanEntry 13 }

arrisRouterSoftGreRadiusServerAddress OBJECT-TYPE
    SYNTAX      InetAddress
    MAX-ACCESS  read-write
    STATUS      current
    DESCRIPTION
        "The internet address of the RADIUS server for this service set.
         If not specified and Radius Enabled, will default to WLAN GW"
    ::= { arrisRouterSoftGreWanEntry 14 }

arrisRouterSoftGreRadiusServerPort OBJECT-TYPE
    SYNTAX      Unsigned32
    MAX-ACCESS  read-write
    STATUS      current
    DESCRIPTION
        "The UDP port used to communicate with the RADIUS server for this
         service set.  Defaults to Port 1812"
    DEFVAL  { 1812 }
    ::= { arrisRouterSoftGreWanEntry 15 }

arrisRouterSoftGreRadiusKey OBJECT-TYPE
    SYNTAX      DisplayString (SIZE(1..64))
    MAX-ACCESS  read-write
    STATUS      current
    DESCRIPTION
        "The RADIUS key."
    ::= { arrisRouterSoftGreWanEntry 16 }

arrisRouterSoftGreRadiusReAuthInterval OBJECT-TYPE
    SYNTAX      Unsigned32
    UNITS       "seconds"
    MAX-ACCESS  read-write
    STATUS      current
    DESCRIPTION
        "The network re-authentication interval.  If set to zero, no
         re-authentication will be performed."
    ::= { arrisRouterSoftGreWanEntry 17 }

arrisRouterSoftGreVlanQEnable  OBJECT-TYPE
     SYNTAX      TruthValue
     MAX-ACCESS  read-write
     STATUS      current
     DESCRIPTION "Enable or disable the VLan Q tag being added to the packet"
     DEFVAL { true }
     ::= { arrisRouterSoftGreWanEntry 18 }

arrisRouterSoftGreWanDscp OBJECT-TYPE
    SYNTAX      DscpOrAny
    MAX-ACCESS  read-write
    STATUS      current
    DESCRIPTION "This object allows the overwrite of the DSCP field per RFC 3260."
    DEFVAL { 0 }
    ::= { arrisRouterSoftGreWanEntry 19 }

arrisRouterSoftGreWanDNSRetryTimer OBJECT-TYPE
     SYNTAX      Unsigned32(30..1800)
     MAX-ACCESS  read-write
     STATUS      current
     DESCRIPTION "Retry timer(seconds) triggered when HHG is unable to resolve the WLAN GW"
     DEFVAL  { 30 }
     ::= { arrisRouterSoftGreWanEntry 20 }

arrisRouterSoftGreWanCurrentControllerIPAddressType OBJECT-TYPE
    SYNTAX      InetAddressType
    MAX-ACCESS  read-only
    STATUS      current
    DESCRIPTION
        "The type of internet address used for current active Hotspot WLAN GW controller."
    ::= { arrisRouterSoftGreWanEntry 21 }

arrisRouterSoftGreWanCurrentControllerIPAddress OBJECT-TYPE
    SYNTAX      InetAddress
    MAX-ACCESS  read-only
    STATUS      current
    DESCRIPTION
        "The internet address of current active Hotspot WLAN GW controller."
    ::= { arrisRouterSoftGreWanEntry 22 }

arrisRouterSoftGreWanPrimaryControllerIPAddressType OBJECT-TYPE
    SYNTAX      InetAddressType
    MAX-ACCESS  read-only
    STATUS      current
    DESCRIPTION
        "The type of internet address used for Primary Hotspot WLAN GW controller in DNS SRV record of FQDN."
    ::= { arrisRouterSoftGreWanEntry 23 }

arrisRouterSoftGreWanPrimaryControllerIPAddress OBJECT-TYPE
    SYNTAX      InetAddress
    MAX-ACCESS  read-only
    STATUS      current
    DESCRIPTION
        "The internet address of Primary Hotspot WLAN GW controller in DNS SRV record of FQDN."
    ::= { arrisRouterSoftGreWanEntry 24 }

arrisRouterSoftGreWanSecondaryControllerIPAddressType OBJECT-TYPE
    SYNTAX      InetAddressType
    MAX-ACCESS  read-only
    STATUS      current
    DESCRIPTION
        "The type of internet address used for Secondary Hotspot WLAN GW controller in DNS SRV record of FQDN."
    ::= { arrisRouterSoftGreWanEntry 25 }

arrisRouterSoftGreWanSecondaryControllerIPAddress OBJECT-TYPE
    SYNTAX      InetAddress
    MAX-ACCESS  read-only
    STATUS      current
    DESCRIPTION
        "The internet address of Secondary Hotspot WLAN GW controller in DNS SRV record of FQDN."
    ::= { arrisRouterSoftGreWanEntry 26 }

arrisRouterSoftGreWanStatus OBJECT-TYPE
    SYNTAX INTEGER {up(0),down(1),error(2)}
    MAX-ACCESS  read-only
    STATUS      current
    DESCRIPTION
        "This MIB object reports the current operational state of tunnel.
         The up(0) state indicates the interface is able to transmit and receive network traffic.
         The down(1) state indicates the interface is prevented from entering the Up(0) state.
         The error(2) state indicates there is an error or other fault condition detected on the interface."
    ::= { arrisRouterSoftGreWanEntry 27 }

arrisRouterSoftGreTransportInterface OBJECT-TYPE
    SYNTAX INTEGER {gwip(0), cmip(1)}
    MAX-ACCESS  read-write
    STATUS      current
    DESCRIPTION
        "The GRE tunnel local IP address, 0 for GW IP, 1 for CM IP. The address type must be same to the
		GRE tunnel server address configured by arrisRouterSoftGreWanControllerFqdn/arrisRouterSoftGreWanControllerProvisionedSecondaryIpAddress."
    DEFVAL { gwip }
    ::= { arrisRouterSoftGreWanEntry 29 }

arrisRouterSoftGreRadiusTransportInterface OBJECT-TYPE
    SYNTAX INTEGER {gwip(0), cmip(1)}
    MAX-ACCESS  read-write
    STATUS      current
    DESCRIPTION
        "The RADIUS local IP address, 0 for GW IP, 1 for CM IP."
    DEFVAL { gwip }
    ::= { arrisRouterSoftGreWanEntry 30 }

arrisRouterSoftGreAcctServerAddressType OBJECT-TYPE
    SYNTAX      InetAddressType
    MAX-ACCESS  read-write
    STATUS      current
    DESCRIPTION
        "The type of internet address used for arrisRouterSoftGreAcctServerAddress."
    ::= { arrisRouterSoftGreWanEntry 31 }

arrisRouterSoftGreAcctServerAddress OBJECT-TYPE
    SYNTAX      InetAddress
    MAX-ACCESS  read-write
    STATUS      current
    DESCRIPTION
        "The internet address of the RADIUS accounting server for this service set.
         If not specified and Radius Enabled, will default to RADIUS authentication server"
    ::= { arrisRouterSoftGreWanEntry 32 }

arrisRouterSoftGreAcctServerPort OBJECT-TYPE
    SYNTAX      Unsigned32
    MAX-ACCESS  read-write
    STATUS      current
    DESCRIPTION
        "The UDP port used to communicate with the RADIUS accounting server for this
         service set.  Defaults to Port 1813"
    DEFVAL  { 1813 }
    ::= { arrisRouterSoftGreWanEntry 33 }

arrisRouterSoftGreAcctKey OBJECT-TYPE
    SYNTAX      DisplayString (SIZE(1..64))
    MAX-ACCESS  read-write
    STATUS      current
    DESCRIPTION
        "The RADIUS accounting key."
    ::= { arrisRouterSoftGreWanEntry 34 }

arrisRouterSoftGreAcctInterval OBJECT-TYPE
    SYNTAX      Unsigned32
    UNITS       "seconds"
    MAX-ACCESS  read-write
    STATUS      current
    DESCRIPTION
        "The RADIUS accounting interim update interval.  If set to zero, no
         accounting update will be performed."
    ::= { arrisRouterSoftGreWanEntry 35 }

arrisRouterSoftGreRadiusSecondaryServerAddressType OBJECT-TYPE
    SYNTAX      InetAddressType
    MAX-ACCESS  read-write
    STATUS      current
    DESCRIPTION
        "The type of internet address used for arrisRouterRadiusSecondaryAddress."
    ::= { arrisRouterSoftGreWanEntry 36 }

arrisRouterSoftGreRadiusSecondaryServerAddress OBJECT-TYPE
    SYNTAX      InetAddress
    MAX-ACCESS  read-write
    STATUS      current
    DESCRIPTION
        "The internet address of the Secondary RADIUS server for this service set."
    ::= { arrisRouterSoftGreWanEntry 37 }

arrisRouterSoftGreRadiusSecondaryServerPort OBJECT-TYPE
    SYNTAX      Unsigned32
    MAX-ACCESS  read-write
    STATUS      current
    DESCRIPTION
        "The UDP port used to communicate with the Secondary RADIUS server for this
         service set.  Defaults to Port 1812"
    DEFVAL  { 1812 }
    ::= { arrisRouterSoftGreWanEntry 38 }

arrisRouterSoftGreRadiusSecondaryKey OBJECT-TYPE
    SYNTAX      DisplayString (SIZE(1..64))
    MAX-ACCESS  read-write
    STATUS      current
    DESCRIPTION
        "The RADIUS key."
    ::= { arrisRouterSoftGreWanEntry 39 }

arrisRouterSoftGreRadiusSecondaryReAuthInterval OBJECT-TYPE
    SYNTAX      Unsigned32
    UNITS       "seconds"
    MAX-ACCESS  read-write
    STATUS      current
    DESCRIPTION
        "The network re-authentication interval of the Secondary RADIUS server.
         If set to zero, no re-authentication will be performed."
    ::= { arrisRouterSoftGreWanEntry 40 }

arrisRouterSoftGreRemoteIdUseCMMac OBJECT-TYPE
     SYNTAX      TruthValue
     MAX-ACCESS  read-write
     STATUS      current
     DESCRIPTION "Enable or disable the RemoteId to use the CM mac address.
                 Set it to true, RemoteId will be the CM mac address.
                 Set it to false, RemoteId will be the mac address of clients connected to hotspot."
     DEFVAL { false }
     ::= { arrisRouterSoftGreWanEntry 41 }

arrisRouterSoftGreRadiusAcctEnabled OBJECT-TYPE
     SYNTAX      TruthValue
     MAX-ACCESS  read-write
     STATUS      current
     DESCRIPTION "Enable or disable Radius Accounting for the SoftGRE Tunnel"
     DEFVAL { false }
     ::= { arrisRouterSoftGreWanEntry 42 }

arrisRouterSoftGreWanFailurePingInterval OBJECT-TYPE
     SYNTAX      INTEGER
     MAX-ACCESS  read-write
     STATUS      current
     DESCRIPTION "Configured interval in seconds for WLAN GW reachability health checks in all GW Failure"
     DEFVAL  { 300 }
     ::= { arrisRouterSoftGreWanEntry 43 }

arrisRouterSoftGreMultiHotspotEnable OBJECT-TYPE
     SYNTAX      TruthValue
     MAX-ACCESS  read-write
     STATUS      current
     DESCRIPTION "Enable or disable all xfinity wifi SSIDS on multi radio device"
     DEFVAL  { false }
     ::= { arrisRouterSoftGreWanEntry 44 }

arrisRouterSoftGreReconnectToPrimary OBJECT-TYPE
     SYNTAX      INTEGER
     MAX-ACCESS  read-write
     STATUS      current
     DESCRIPTION "Configured interval after which the XWG should switch back to primary"
     DEFVAL  { 7200 }
     ::= { arrisRouterSoftGreWanEntry 58 }

arrisRouterSoftGreTunnelUpTime OBJECT-TYPE
     SYNTAX      INTEGER
     MAX-ACCESS  read-only
     STATUS      current
     DESCRIPTION "Indicates the duration for which the current tunnel is up"
     DEFVAL  {  360 }
     ::= { arrisRouterSoftGreWanEntry 59 }

arrisRouterSoftGreWanActiveMonitoringTimer OBJECT-TYPE
     SYNTAX      INTEGER
     MAX-ACCESS  read-write
     STATUS      current
     DESCRIPTION "Time taken for AP to attempt active monitoring [DHCP Request/NAK] on each gateway until one of the WLAN-GW becomes available"
     DEFVAL  { 300 }
     ::= { arrisRouterSoftGreWanEntry 60 }

arrisRouterSoftGreWanPassiveMonitoringTimer OBJECT-TYPE
     SYNTAX      INTEGER
     MAX-ACCESS  read-write
     STATUS      current
     DESCRIPTION "The window time for packets sent from the AP to the WLAN GW and returned, within passive data monitoring"
     DEFVAL  { 160 }
     ::= { arrisRouterSoftGreWanEntry 61 }

arrisRouterSoftGreWanActiveMonitoringDhcpIpAddressFqdn OBJECT-TYPE
     SYNTAX      DisplayString (SIZE(0..255))
     MAX-ACCESS  read-write
     STATUS      current
     DESCRIPTION "The IP sent by AP with IP outside the DHCP pool in the server "
     ::= { arrisRouterSoftGreWanEntry 62 }

arrisRouterSoftGreSSIDTable OBJECT-TYPE
     SYNTAX      SEQUENCE OF ArrisRouterSoftGreSSIDEntry
     MAX-ACCESS  not-accessible
     STATUS      current
     DESCRIPTION "Table contains information to be assigned per SSID across GRE tunnel.
                  Table is 1 based"
     ::= { arrisRouterSoftGreWanObjects 2 }

arrisRouterSoftGreSSIDEntry OBJECT-TYPE
     SYNTAX      ArrisRouterSoftGreSSIDEntry
     MAX-ACCESS  not-accessible
     STATUS      current
     DESCRIPTION "Table contains the information to be assigned per SSID across GRE tunnel.
                  Index is the SSID"
     INDEX { ifIndex }	--from IF-MIB
     ::= { arrisRouterSoftGreSSIDTable 1 }

ArrisRouterSoftGreSSIDEntry ::= SEQUENCE {
     arrisRouterSoftGreVLanId              Unsigned32,
     arrisRouterSoftGreVLanPriority       Unsigned32,
     arrisRouterSoftGreSSIDEnable         TruthValue,
     arrisRouterSoftGreDHCPOption60Enable TruthValue,
     arrisRouterSoftGreSSIDMappedToTunnelEnable INTEGER
}

arrisRouterSoftGreVLanId  OBJECT-TYPE
    SYNTAX      Unsigned32
    MAX-ACCESS  read-write
    STATUS      current
    DESCRIPTION "The VLan ID to be used for this managed SSID.
                 Set to zero to not use VLan."
    DEFVAL { 0 }
    ::= { arrisRouterSoftGreSSIDEntry  1 }

arrisRouterSoftGreVLanPriority  OBJECT-TYPE
    SYNTAX      Unsigned32
    MAX-ACCESS  read-write
    STATUS      current
    DESCRIPTION "The VLan Priority to be used for this managed SSID."
    DEFVAL { 0 }
    ::= { arrisRouterSoftGreSSIDEntry  2 }

arrisRouterSoftGreSSIDEnable OBJECT-TYPE
     SYNTAX      TruthValue
     MAX-ACCESS  read-write
     STATUS      current
     DESCRIPTION "Enable or disable this SoftGRE mapped SSID."
     DEFVAL { true }
     ::= { arrisRouterSoftGreSSIDEntry 3 }

arrisRouterSoftGreDHCPOption60Enable OBJECT-TYPE
     SYNTAX      TruthValue
     MAX-ACCESS  read-write
     STATUS      current
     DESCRIPTION "Enable or disable SSID name being inserted to DHCP Option 60."
     DEFVAL { false }
     ::= { arrisRouterSoftGreSSIDEntry 4 }

arrisRouterSoftGreSSIDMappedToTunnelEnable OBJECT-TYPE
     SYNTAX      INTEGER { notMappedToTunnel(0), mappedToTunnel1(1), mappedToTunnel2(2) , mappedToTunnel3(3) , mappedToTunnel4(4)  }
     MAX-ACCESS  read-write
     STATUS      current
     DESCRIPTION "Enable xfinity wifi SSIDs mapping to specific Tunnel .
                 Based on these values, the value of mapped interfaces will be
                 automatically assigned to arrisRouterSoftGreMappedInterface .
                 Set the managed SSID to the specific GRE Tunnel"
     DEFVAL  { 1 }
     ::= { arrisRouterSoftGreSSIDEntry 5 }

arrisRouterSoftGreCustomerOptOut OBJECT-TYPE
     SYNTAX      TruthValue
     MAX-ACCESS  read-write
     STATUS      current
     DESCRIPTION "If the user has opted out of the service, setting this value to true
                  the Gateway will ignore any of the provisioned HotSpot Configuration
                  from the config file."
     DEFVAL { false }
     ::= { arrisRouterSoftGreWanObjects 3 }

arrisRouterSoftGreRestore OBJECT-TYPE
     SYNTAX      TruthValue
     MAX-ACCESS  read-write
     STATUS      current
     DESCRIPTION "Restore XWiFi settings to factory default."
     DEFVAL { false }
     ::= { arrisRouterSoftGreWanObjects 4 }

arrisRouterSoftGreCapable OBJECT-TYPE
     SYNTAX      TruthValue
     MAX-ACCESS  read-only
     STATUS      current
     DESCRIPTION "Indicates if the softGRE/Hotspot feature is available on this device."
     DEFVAL { true }
     ::= { arrisRouterSoftGreWanObjects 5 }

arrisRouterDHCPRelayAgentWanObjects   OBJECT IDENTIFIER ::= { arrisRouterWanConfig 20 }

arrisRouterDHCPRelayAgentSSIDTable OBJECT-TYPE
     SYNTAX      SEQUENCE OF ArrisRouterDHCPRelayAgentSSIDEntry
     MAX-ACCESS  not-accessible
     STATUS      current
     DESCRIPTION "Table contains information to be assigned per SSID with DHCP Relay.
                  Table is 1 based"
     ::= { arrisRouterDHCPRelayAgentWanObjects 1 }


arrisRouterDHCPRelayAgentSSIDEntry OBJECT-TYPE
     SYNTAX      ArrisRouterDHCPRelayAgentSSIDEntry
     MAX-ACCESS  not-accessible
     STATUS      current
     DESCRIPTION "Table contains the information to be assigned per SSID with DHCP Relay.
                  Index is the SSID."
     INDEX { ifIndex }	--from IF-MIB
     ::= { arrisRouterDHCPRelayAgentSSIDTable 1 }

ArrisRouterDHCPRelayAgentSSIDEntry ::= SEQUENCE {
     arrisRouterDHCPRelayAgentEnable                TruthValue,
     arrisRouterDHCPRelayAgentCircuitIdEnabled      TruthValue,
     arrisRouterDHCPRelayAgentRemoteIdEnabled       TruthValue,
     arrisRouterDHCPRelayAgentOption60SSIDEnabled   TruthValue
}

arrisRouterDHCPRelayAgentEnable OBJECT-TYPE
     SYNTAX      TruthValue
     MAX-ACCESS  read-write
     STATUS      current
     DESCRIPTION "Enable or disable the DHCPRelayAgent.
                 This DHCPRelayAgent feature is only working on bridge mode."
     DEFVAL { true }
     ::= { arrisRouterDHCPRelayAgentSSIDEntry 1 }

arrisRouterDHCPRelayAgentCircuitIdEnabled OBJECT-TYPE
     SYNTAX      TruthValue
     MAX-ACCESS  read-write
     STATUS      current
     DESCRIPTION "Enable or disable the Circuit ID being added to DHCP"
     DEFVAL { true }
     ::= { arrisRouterDHCPRelayAgentSSIDEntry 2 }

arrisRouterDHCPRelayAgentRemoteIdEnabled OBJECT-TYPE
     SYNTAX      TruthValue
     MAX-ACCESS  read-write
     STATUS      current
     DESCRIPTION "Enable or disable the RemoteId being added to DHCP"
     DEFVAL { true }
     ::= { arrisRouterDHCPRelayAgentSSIDEntry 3 }

arrisRouterDHCPRelayAgentOption60SSIDEnabled OBJECT-TYPE
     SYNTAX      TruthValue
     MAX-ACCESS  read-write
     STATUS      current
     DESCRIPTION "Enable or disable the SSID name being inserted to the beginning of DHCP Option 60"
     DEFVAL { false }
     ::= { arrisRouterDHCPRelayAgentSSIDEntry 4 }

arrisRouterWanTR181GatewayInfoObjects   OBJECT IDENTIFIER ::= { arrisRouterWanConfig 21 }

arrisRouterTR181GatewayManufacturerOUI OBJECT-TYPE
     SYNTAX      DisplayString (SIZE (0..6))
     MAX-ACCESS  read-only
     STATUS      current
     DESCRIPTION "Organizationally unique identifier of the associated Internet Gateway Device.
                  Possible patterns:
                   - <Empty> (an empty string)
                   - [0-9A-F]{6} "
     ::= { arrisRouterWanTR181GatewayInfoObjects 1 }

arrisRouterTR181GatewayProductClass OBJECT-TYPE
     SYNTAX      DisplayString (SIZE (0..64))
     MAX-ACCESS  read-only
     STATUS      current
     DESCRIPTION "Identifier of the product class of the associated Internet Gateway Device."
     ::= { arrisRouterWanTR181GatewayInfoObjects 2 }

arrisRouterTR181GatewaySerialNumber OBJECT-TYPE
     SYNTAX      DisplayString (SIZE (0..64))
     MAX-ACCESS  read-only
     STATUS      current
     DESCRIPTION "Serial number of the associated Internet Gateway Device."
     ::= { arrisRouterWanTR181GatewayInfoObjects 3 }

arrisRouterWanForceIGMPVersion OBJECT-TYPE
     SYNTAX      INTEGER { auto(0),igmpv1(1), igmpv2(2), igmpv3(3) }
     MAX-ACCESS  read-write
     STATUS      current
     DESCRIPTION "Forces eRouter using the specific IGMP Version in the WAN side.
                  see the Linux proc file /proc/sys/net/ipv4/conf/lbr0/force_igmp_version (for TS7.x)
                  or /proc/sys/net/ipv4/conf/erouter0/force_igmp_version (for TS9.x) for reference"
     ::= { arrisRouterWanConfig 22 }

arrisRouterWanIPUnderBridge OBJECT-TYPE
     SYNTAX      TruthValue
     MAX-ACCESS  read-write
     STATUS      current
     DESCRIPTION "eRouter gets WAN IP address in bridge mode.
                  When set to false, eRouter would not use any WAN IP address in bridge mode."
     DEFVAL { true }
     ::= { arrisRouterWanConfig 23 }

arrisRouterWanRtspUdpTimeout OBJECT-TYPE
     SYNTAX      INTEGER
     MAX-ACCESS  read-write
     STATUS      current
     DESCRIPTION "Set the value of UDP conntrack timeout for RTSP session"
     ::= { arrisRouterWanConfig 24 }

arrisRouterWanRtspUdpStreamTimeout OBJECT-TYPE
     SYNTAX      INTEGER
     MAX-ACCESS  read-write
     STATUS      current
     DESCRIPTION "Set the value of UDP stream conntrack timeout for RTSP session"
     ::= { arrisRouterWanConfig 25 }

-- lan table

arrisRouterLanCount OBJECT-TYPE
      SYNTAX      Unsigned32
      MAX-ACCESS  read-only
      STATUS      current
      DESCRIPTION "The number of Lans configured on this device.  This corresponds to the row count for arris RouterLanTable."
      ::= { arrisRouterLanConfig 1 }

arrisRouterLanSrvTable OBJECT-TYPE
      SYNTAX      SEQUENCE OF ArrisRouterLanSrvEntry
      MAX-ACCESS  not-accessible
      STATUS      current
      DESCRIPTION "Table contains information for a specific Lan."
      ::= { arrisRouterLanConfig 2 }

arrisRouterLanSrvEntry OBJECT-TYPE
      SYNTAX      ArrisRouterLanSrvEntry
      MAX-ACCESS  not-accessible
      STATUS      current
      DESCRIPTION "Table contains information for a specific Lan."
      INDEX { ifIndex }	--from IF-MIB
      ::= { arrisRouterLanSrvTable 1 }

ArrisRouterLanSrvEntry ::= SEQUENCE {
        arrisRouterLanName						DisplayString,
        arrisRouterLanSubnetMaskType 			InetAddressType,
        arrisRouterLanSubnetMask 				InetAddress,
        arrisRouterLanGatewayIpType 			InetAddressType,
        arrisRouterLanGatewayIp 				InetAddress,
        arrisRouterLanGatewayIp2Type 			InetAddressType,
        arrisRouterLanGatewayIp2 				InetAddress,
        arrisRouterLanVLanID					Unsigned32,
        arrisRouterLanUseDHCP					TruthValue,
        arrisRouterLanStartDHCPType				InetAddressType,
        arrisRouterLanStartDHCP					InetAddress,
        arrisRouterLanEndDHCPType				InetAddressType,
        arrisRouterLanEndDHCP					InetAddress,
        arrisRouterLanLeaseTime					Unsigned32,
        arrisRouterLanDomainName				DisplayString,
        arrisRouterLanRateLimit					TruthValue,
        arrisRouterLanDownRateLimit				Unsigned32,
        arrisRouterLanUpRateLimit				Unsigned32,
        arrisRouterLanRelayDNS					TruthValue,
        arrisRouterLanIPv6Mode					INTEGER,
        arrisRouterLanPassThru					INTEGER,
        arrisRouterLanFirewallOn				TruthValue,
        arrisRouterLanUPnPEnable				TruthValue,
        arrisRouterLanCPEAging					Integer32,
        arrisRouterLanOverrideDNS				TruthValue,
        arrisRouterLanNatAlgsEnabled                            BITS,
        arrisRouterLanMappedInterface                           Unsigned32,
        arrisRouterLanEnvironmentControl                        INTEGER,
        arrisRouterLanPrefixLengthV6                            InetAddressPrefixLength,
        arrisRouterLanUseDHCPV6					TruthValue,
        arrisRouterLanStartDHCPV6				InetAddressIPv6,
        arrisRouterLanEndDHCPV6					InetAddressIPv6,
        arrisRouterLanLeaseTimeV6				Unsigned32,
        arrisRouterLanLinkLocalAddressV6                        InetAddressIPv6,
        arrisRouterLanDNSRelayV6	                        TruthValue,
        arrisRouterLanDNSOverrideV6	                        TruthValue,
        arrisRouterLanPreProvLeaseTime                          Unsigned32,
        arrisRouterAdminBridgeOptionDisplay                     TruthValue,
        arrisRouterLanParentalControlsEnable                    TruthValue,
        arrisRouterLanWlanIsolate                               TruthValue
	}

arrisRouterLanName OBJECT-TYPE
     SYNTAX      DisplayString (SIZE (0..32))
     MAX-ACCESS  read-write
     STATUS      current
     DESCRIPTION "Textual name of this Lan.
                  NOTE: For TS7.x, this mib has read-only access property."
     ::= { arrisRouterLanSrvEntry 1 }

arrisRouterLanSubnetMaskType OBJECT-TYPE
      SYNTAX      InetAddressType
      MAX-ACCESS  read-create
      STATUS      current
      DESCRIPTION
          "Ip Address Type of the SubnetMask for a specific Network."
      DEFVAL { ipv4 }
      ::= { arrisRouterLanSrvEntry 2 }

arrisRouterLanSubnetMask OBJECT-TYPE
      SYNTAX      InetAddress
      MAX-ACCESS  read-create
      STATUS      current
      DESCRIPTION
          "Ip Address of the SubnetMask for a specific Network."
      ::= { arrisRouterLanSrvEntry 3 }

arrisRouterLanGatewayIpType OBJECT-TYPE
      SYNTAX      InetAddressType
      MAX-ACCESS  read-create
      STATUS      current
      DESCRIPTION
          "Ip Address Type of the Gateway for a specific Network."
      DEFVAL { ipv4 }
      ::= { arrisRouterLanSrvEntry 4 }

arrisRouterLanGatewayIp OBJECT-TYPE
      SYNTAX      InetAddress
      MAX-ACCESS  read-create
      STATUS      current
      DESCRIPTION
          "Ip Address of the Gateway for a specific Network."
      ::= { arrisRouterLanSrvEntry 5 }

arrisRouterLanGatewayIp2Type OBJECT-TYPE
      SYNTAX      InetAddressType
      MAX-ACCESS  read-create
      STATUS      current
      DESCRIPTION
          "Ip Address Type of the Gateway for a specific Network."
      DEFVAL { ipv4 }
      ::= { arrisRouterLanSrvEntry 6 }

arrisRouterLanGatewayIp2 OBJECT-TYPE
      SYNTAX      InetAddress
      MAX-ACCESS  read-create
      STATUS      current
      DESCRIPTION
          "Ip Address of the Gateway for a specific Network."
      ::= { arrisRouterLanSrvEntry 7 }

arrisRouterLanVLanID OBJECT-TYPE
     SYNTAX      Unsigned32
     MAX-ACCESS  read-write
     STATUS      current
     DESCRIPTION "The VLan ID to be used for this Lan.  Set to zero to not use VLan."
     DEFVAL	{ 0 }
     ::= { arrisRouterLanSrvEntry 8 }

arrisRouterLanUseDHCP OBJECT-TYPE
     SYNTAX      TruthValue
     MAX-ACCESS  read-write
     STATUS      current
     DESCRIPTION "Enable or disable the local DHCP server on this VLan."
     DEFVAL	{ true }
     ::= { arrisRouterLanSrvEntry 9 }

arrisRouterLanStartDHCPType OBJECT-TYPE
     SYNTAX      InetAddressType
     MAX-ACCESS  read-write
     STATUS      current
     DESCRIPTION "The type of IP address for the start of the range of IP addresses to be handed out by this DHCP server."
     ::= { arrisRouterLanSrvEntry 10 }

arrisRouterLanStartDHCP OBJECT-TYPE
     SYNTAX      InetAddress
     MAX-ACCESS  read-write
     STATUS      current
     DESCRIPTION "The start of the range of IP addresses to be handed out by this DHCP server."
     ::= { arrisRouterLanSrvEntry 11 }

arrisRouterLanEndDHCPType OBJECT-TYPE
     SYNTAX      InetAddressType
     MAX-ACCESS  read-write
     STATUS      current
     DESCRIPTION "The type of IP address for the end of the range of IP addresses to be handed out by this DHCP server."
     ::= { arrisRouterLanSrvEntry 12 }

arrisRouterLanEndDHCP OBJECT-TYPE
     SYNTAX      InetAddress
     MAX-ACCESS  read-write
     STATUS      current
     DESCRIPTION "The end of the range of IP addresses to be handed out by this DHCP server."
     ::= { arrisRouterLanSrvEntry 13 }

arrisRouterLanLeaseTime OBJECT-TYPE
     SYNTAX      Unsigned32
     UNITS       "seconds"
     MAX-ACCESS  read-write
     STATUS      current
     DESCRIPTION "The length of the lease time for dynamic (DHCP) IP addresses handed out by this device."
     ::= { arrisRouterLanSrvEntry 14 }

arrisRouterLanDomainName OBJECT-TYPE
     SYNTAX      DisplayString (SIZE (0..64))
     MAX-ACCESS  read-write
     STATUS      current
     DESCRIPTION "Optional domain name for this lan."
     ::= { arrisRouterLanSrvEntry 15 }

arrisRouterLanRateLimit OBJECT-TYPE
     SYNTAX      TruthValue
     MAX-ACCESS  read-write
     STATUS      current
     DESCRIPTION "Enable or disable rate limiting on this Lan."
     DEFVAL	{ false }
     ::= { arrisRouterLanSrvEntry 16 }

arrisRouterLanDownRateLimit OBJECT-TYPE
     SYNTAX      Unsigned32
     UNITS		 "kb/s"
     MAX-ACCESS  read-write
     STATUS      current
     DESCRIPTION "The downlink limiting rate.  Use zero for no rate limiting."
     DEFVAL	{ 0 }
     ::= { arrisRouterLanSrvEntry 17 }

arrisRouterLanUpRateLimit OBJECT-TYPE
     SYNTAX      Unsigned32
     UNITS		 "kb/s"
     MAX-ACCESS  read-write
     STATUS      current
     DESCRIPTION "The uplink limiting rate.  Use zero for no rate limiting."
     DEFVAL	{ 0 }
     ::= { arrisRouterLanSrvEntry 18 }

arrisRouterLanRelayDNS OBJECT-TYPE
     SYNTAX      TruthValue
     MAX-ACCESS  read-write
     STATUS      current
     DESCRIPTION "Enable or disable DNS relay."
     DEFVAL	{ false }
     ::= { arrisRouterLanSrvEntry 19 }

arrisRouterLanIPv6Mode OBJECT-TYPE
     SYNTAX      INTEGER { linkLocalOnly(1), siteLocalOnly(2) }
     MAX-ACCESS  read-write
     STATUS      current
     DESCRIPTION "IPv6 setting."
     ::= { arrisRouterLanSrvEntry 20 }

arrisRouterLanPassThru OBJECT-TYPE
     SYNTAX      INTEGER { unknown(-1), passThru(1), routedNAT(2), routedNoNAT(3) }
     MAX-ACCESS  read-write
     STATUS      current
     DESCRIPTION "Get/set whether or not this Lan is in pass-thru mode or bridged/NAT.
                    To put the device into bridged mode with routing and NAT disabled -- pass-thru, use: passThru(1).
                    To put the device into non-bridged (routed) mode with Network Address Translation (NAT) enabled use: routedNAT(2).
                    To put the device into non-bridged (routed) mode with Network Address Translation (NAT) disabled use: routedNoNAT(3)."
	 DEFVAL { routedNAT }
     ::= { arrisRouterLanSrvEntry 21 }

arrisRouterLanFirewallOn OBJECT-TYPE
     SYNTAX      TruthValue
     MAX-ACCESS  read-write
     STATUS      current
     DESCRIPTION "Get/set whether or not the firewall is applied to this Lan."
     ::= { arrisRouterLanSrvEntry 22 }

arrisRouterLanUPnPEnable OBJECT-TYPE
     SYNTAX      TruthValue
     MAX-ACCESS  read-write
     STATUS      current
     DESCRIPTION "Get/set whether or not UPnP is enabled for this Lan."
     ::= { arrisRouterLanSrvEntry 23 }

arrisRouterLanCPEAging OBJECT-TYPE
     SYNTAX      Integer32
     MAX-ACCESS  read-write
     STATUS      current
     DESCRIPTION "The timeout period in seconds for aging out
                    dynamically learned forwarding information.
                    The default value of zero means do not age"
     ::= { arrisRouterLanSrvEntry 24 }

arrisRouterLanOverrideDNS OBJECT-TYPE
     SYNTAX      TruthValue
     MAX-ACCESS  read-write
     STATUS      current
     DESCRIPTION "Enable or disable DNS override.  If DNS override is true the IP addresses in arrisRouterLanDNSTable will be passed to LAN clients via DHCP.
                    Otherwise, the DNS servers received by the WAN connection will be passed to the LAN clients."
     DEFVAL	{ false }
     ::= { arrisRouterLanSrvEntry 25 }

arrisRouterLanNatAlgsEnabled OBJECT-TYPE
     SYNTAX      BITS {
                    rsvp(0),       -- US/DS; IP 46 (Reserved)
                    ftp(1),        -- US/DS; TCP 21
                    tftp(2),       -- US; UDP 17
                    kerb88(3),     -- US; UDP 88 (Reserved)
                    netBiosDgm(4), -- US; UDP 138 (Reserved)
                    ike(5),        -- US/DS; UDP 500 (Reserved)
                    rtsp(6),       -- US/DS; TCP 554 (Reserved)
                    kerb1293(7),   -- US; UDP 1293 (Reserved)
                    h225(8),       -- US/DS; TCP 1720
                    pptp(9),       -- US/DS; TCP 1723
                    msn(10),       -- US/DS; TCP 1863 (Reserved)
                    sip(11),       -- US; UDP 5060
                    icq(12),       -- US; TCP 5190 (Reserved)
                    irc6667(13),   -- US; TCP 6667
                    icqTalk(14),   -- US/DS; UDP 6701 (Reserved)
                    net2Phone(15), -- US/DS; UDP 6801 (Reserved)
                    irc7000(16),   -- US; TCP 7000 (Reserved)
                    irc8000(17)    -- US; TCP 8000 (Reserved)
                 }
    MAX-ACCESS  read-write
    STATUS      current
    DESCRIPTION
     "Specifies which NAT application layer gateway supplements are enabled
      on this device.  The default value for this object is for all ALG's
      to be enabled. Reserved bits are for ALGs that are currently not supported."
    ::= { arrisRouterLanSrvEntry 26 }

arrisRouterLanMappedInterface OBJECT-TYPE
     SYNTAX      Unsigned32
     MAX-ACCESS  read-write
     STATUS      current
     DESCRIPTION "Name of the member physical network interface (or virtual network interface in
                  the case of a wireless SSID) comprising the logical interface, aka LAN subnet.
                  This mib object takes in an unsigned integer with the following bitmap setup:

                  Single-Band support:
		  0x00000001 // ethernet
		  0x00000002 // usb (unsupported)
		  0x00000004 // moca
		  0x00000008 // ssid1
		  0x00000010 // ssid2
		  0x00000020 // ssid3
		  0x00000040 // ssid4
		  0x00000080 // ssid5
		  0x00000100 // ssid6
		  0x00000200 // ssid7
		  0x00000400 // ssid8

		  Dual-Band support:
		  0x00000001 // ethernet
		  0x00000002 // usb (unsupported)
		  0x00000004 // moca
		  0x00000008 // ssid1 & ssid9
		  0x00000010 // ssid2 & ssid10
		  0x00000020 // ssid3 & ssid11
		  0x00000040 // ssid4 & ssid12
		  0x00000080 // ssid5 & ssid13
		  0x00000100 // ssid6 & ssid14
		  0x00000200 // ssid7 & ssid15
		  0x00000400 // ssid8 & ssid16

                  Example of mapping the ethernet, usb, moca, and ssid1 to the primary LAN subnet:
                  0x0000000F = (Integer) 15

                  NOTE - A physical/virtual interface may not be assigned to more than one logical interface."
     ::= { arrisRouterLanSrvEntry 27 }

arrisRouterLanEnvironmentControl OBJECT-TYPE
     SYNTAX      INTEGER { unlocked(0), locked(1) }
     MAX-ACCESS  read-write
     STATUS      current
     DESCRIPTION "Controls whether or not the settings which define the operating environment of
                  the logical interface, aka LAN subnet, are changeable via the GUI.

                  When equal to unlocked, the environment settings MAY be changed via the UI.
                  When equal to locked, the environment settings MAY NOT be changed via the UI."
     DEFVAL { unlocked }
     ::= { arrisRouterLanSrvEntry 28 }

arrisRouterLanPrefixLengthV6 OBJECT-TYPE
     SYNTAX      InetAddressPrefixLength
     MAX-ACCESS  read-only
     STATUS      current
     DESCRIPTION "IPV6 The length indicating the routable portion of the prefix.
                  This length is advertised to the host either through DHCP or
		  router advertisement.  The host uses this length as a clue to generate
		  the rest of the bits which makes up its 128-bit address."
     ::= { arrisRouterLanSrvEntry 29 }

arrisRouterLanUseDHCPV6 OBJECT-TYPE
     SYNTAX      TruthValue
     MAX-ACCESS  read-write
     STATUS      current
     DESCRIPTION "IPV6 Enable or disable the local DHCPv6 server on this VLan."
     DEFVAL	{ true }
     ::= { arrisRouterLanSrvEntry 30 }

arrisRouterLanStartDHCPV6 OBJECT-TYPE
     SYNTAX      InetAddressIPv6
     MAX-ACCESS  read-write
     STATUS      current
     DESCRIPTION "IPV6 The start of the range of IP addresses to be handed out by this DHCP server.
                  NOTE - Only 128 - prefix_length(arrisRouterLanPrefixLengthV6) bits should be configured."
     ::= { arrisRouterLanSrvEntry 31 }

arrisRouterLanEndDHCPV6 OBJECT-TYPE
     SYNTAX      InetAddressIPv6
     MAX-ACCESS  read-write
     STATUS      current
     DESCRIPTION "IPV6 The end of the range of IP addresses to be handed out by this DHCP instace.
                  NOTE - Only 128 - prefix_length(arrisRouterLanPrefixLengthV6) bits should be configured."
     ::= { arrisRouterLanSrvEntry 32 }

arrisRouterLanLeaseTimeV6 OBJECT-TYPE
     SYNTAX      Unsigned32
     UNITS		 "seconds"
     MAX-ACCESS  read-write
     STATUS      current
     DESCRIPTION "IPV6 lease time for dynamic (DHCP) IP addresses handed out by this DHCP server.
                  For the LGI customer,
                    1. If set to zero, the DHCPv6 server lease time uses the same value as the lease time of the prefix delegation.
                    2. If set to positive value(range from 120 secs to 0xffffffff), the DHCPv6 server will use that value as the lease time.
                  For the Other customers, the lease time can range from 120 secs to 0xffffffff."
     ::= { arrisRouterLanSrvEntry 33 }

arrisRouterLanLinkLocalAddressV6 OBJECT-TYPE
     SYNTAX      InetAddressIPv6
     MAX-ACCESS  read-write
     STATUS      current
     DESCRIPTION "IPV6 Link local IPV6 address."
     ::= { arrisRouterLanSrvEntry 34 }

arrisRouterLanDNSRelayV6 OBJECT-TYPE
     SYNTAX      TruthValue
     MAX-ACCESS  read-write
     STATUS      current
     DESCRIPTION "IPV6 Enable or disable DNS relay."
     DEFVAL	{ false }
     ::= { arrisRouterLanSrvEntry 35 }

arrisRouterLanDNSOverrideV6 OBJECT-TYPE
     SYNTAX      TruthValue
     MAX-ACCESS  read-write
     STATUS      current
     DESCRIPTION "IPV6 Enable or disable DNS override.  If DNS override is true the IPv6 addresses in
                  arrisRouterLanDNSTable will be passed to LAN clients via DHCPv6.  Otherwise, the DNS
                  servers received by the WAN connection will be passed to the LAN clients."
     DEFVAL	{ false }
     ::= { arrisRouterLanSrvEntry 36 }

arrisRouterLanPreProvLeaseTime OBJECT-TYPE
     SYNTAX      Unsigned32
     UNITS       "seconds"
     MAX-ACCESS  read-write
     STATUS      current
     DESCRIPTION "The length of the lease time for dynamic (DHCP) IP addresses
                  handed out by this device prior to Gateway provisioning."
     ::= { arrisRouterLanSrvEntry 37 }

arrisRouterAdminBridgeOptionDisplay OBJECT-TYPE
     SYNTAX      TruthValue
     MAX-ACCESS  read-write
     STATUS      current
     DESCRIPTION "Control the display of bridge mode enable/disable button in WEB UI for admin user.
                 true(1): Display the bridge mode enable/disable button on the USERADMIN page.
                 false(2): Hide the bridge mode enable/disable button on the USERADMIN page."
     ::= { arrisRouterLanSrvEntry 38 }

arrisRouterLanParentalControlsEnable OBJECT-TYPE
     SYNTAX      TruthValue
     MAX-ACCESS  read-write
     STATUS      current
     DESCRIPTION "Enable or disable the Parent Control to this subnet."
     DEFVAL { false }
     ::= { arrisRouterLanSrvEntry 39 }

arrisRouterLanWlanIsolate OBJECT-TYPE
     SYNTAX      TruthValue
     MAX-ACCESS  read-write
     STATUS      current
     DESCRIPTION "Isolate 2.4G 5G traffic of this subnet. When this enabled, the traffic between 2.G and 5G will be isolated."
     DEFVAL { false }
     ::= { arrisRouterLanSrvEntry 40 }

arrisRouterLanDNSTable OBJECT-TYPE
      SYNTAX      SEQUENCE OF ArrisRouterLanDNSEntry
      MAX-ACCESS  not-accessible
      STATUS      current
      DESCRIPTION "Table contains DSN server information for a specific Lan."
      ::= { arrisRouterLanConfig 3 }

arrisRouterLanDNSEntry OBJECT-TYPE
      SYNTAX      ArrisRouterLanDNSEntry
      MAX-ACCESS  not-accessible
      STATUS      current
      DESCRIPTION "Table contains DNS server information for a specific Lan."
      INDEX { ifIndex, arrisRouterLanDNSIdx }	--from IF-MIB
      ::= { arrisRouterLanDNSTable 1 }

ArrisRouterLanDNSEntry ::= SEQUENCE {
        arrisRouterLanDNSIdx				Unsigned32,
        arrisRouterLanDNSIPAddrType 		InetAddressType,
        arrisRouterLanDNSIPAddr 			InetAddress,
        arrisRouterLanDNSRowStatus			RowStatus
        }

arrisRouterLanDNSIdx OBJECT-TYPE
     SYNTAX      Unsigned32 (1..6)
     MAX-ACCESS  not-accessible
     STATUS      current
     DESCRIPTION "Table index, also corresponds to the order/priority of the DNS servers for lookups.
                  Current implementation only supports 3 IPv4 and 3 IPv6 DNS servers.
		  NOTE: For TS7.x, this mib only supports (1..4), that is, current implementation only
		  supports 2 IPv4 and 2 IPv6 DNS servers."
     ::= { arrisRouterLanDNSEntry 1 }

arrisRouterLanDNSIPAddrType OBJECT-TYPE
     SYNTAX      InetAddressType
     MAX-ACCESS  read-create
     STATUS      current
     DESCRIPTION "Internet address type for the DNS server."
     ::= { arrisRouterLanDNSEntry 2 }

arrisRouterLanDNSIPAddr OBJECT-TYPE
     SYNTAX      InetAddress
     MAX-ACCESS  read-create
     STATUS      current
     DESCRIPTION "Internet address for the DNS server."
     ::= { arrisRouterLanDNSEntry 3 }

arrisRouterLanDNSRowStatus OBJECT-TYPE
     SYNTAX      RowStatus
     MAX-ACCESS  read-create
     STATUS      current
     DESCRIPTION "RowStatus used to add or remove DNS row entries."
     ::= { arrisRouterLanDNSEntry 4 }

-- arrisRouterLanDNSEntry End

-- list of currently connected clients

arrisRouterClientObjects		OBJECT IDENTIFIER ::= { arrisRouterLanConfig 4 }

arrisRouterLanClientCount OBJECT-TYPE
     SYNTAX      Unsigned32
     MAX-ACCESS  read-only
     STATUS      current
     DESCRIPTION "Current count of clients on this Lan.  This corresponds to the number of rows in arrisRouterLanClientTable"
     ::= { arrisRouterClientObjects 1 }

arrisRouterLanClientTable OBJECT-TYPE
      SYNTAX      SEQUENCE OF ArrisRouterLanClientEntry
      MAX-ACCESS  not-accessible
      STATUS      current
      DESCRIPTION "Table contains the set of DHCP clients for this Lan."
      ::= { arrisRouterClientObjects 2 }

arrisRouterLanClientEntry OBJECT-TYPE
      SYNTAX      ArrisRouterLanClientEntry
      MAX-ACCESS  not-accessible
      STATUS      current
      DESCRIPTION "Table contains the set of DHCP clients for this Lan."
      INDEX { ifIndex, arrisRouterLanClientIPAddrType, arrisRouterLanClientIPAddr }
      ::= { arrisRouterLanClientTable 1 }

ArrisRouterLanClientEntry ::= SEQUENCE {
        arrisRouterLanClientIPAddrType		InetAddressType,
        arrisRouterLanClientIPAddr		InetAddress,
        arrisRouterLanClientHostName		DisplayString,
        arrisRouterLanClientMAC			MacAddress,
        arrisRouterLanClientMACMfg		DisplayString,
        arrisRouterLanClientAdapterType		INTEGER,
        arrisRouterLanClientType		INTEGER,
        arrisRouterLanClientLeaseStart		DateAndTime,
        arrisRouterLanClientLeaseEnd		DateAndTime,
        arrisRouterLanClientStatus		INTEGER,
        arrisRouterLanClientInfLease		INTEGER,
        arrisRouterLanClientLeaseState		INTEGER,
        arrisRouterLanClientRowStatus		RowStatus,
        arrisRouterLanClientOnline		INTEGER,
        arrisRouterLanClientComment		DisplayString,
        arrisRouterLanClientCustom		INTEGER,
        arrisRouterLanClientManufacturerOUI     DisplayString,
        arrisRouterLanClientSerialNumber        DisplayString,
        arrisRouterLanClientProductClass        DisplayString,
        arrisRouterLanClientDeviceName          DisplayString,
        arrisRouterLanClientRSSI                INTEGER,
        arrisRouterLanClientLinkLocalAddrType   InetAddressType,
        arrisRouterLanClientLinkLocalAddr       InetAddress,
        arrisRouterLanClientLastChange          Integer32,
        arrisRouterLanClientTimeConnected       Integer32
        }

arrisRouterLanClientIPAddrType OBJECT-TYPE
     SYNTAX      InetAddressType
     MAX-ACCESS  not-accessible
     STATUS      current
     DESCRIPTION "Current IP address type for the DHCP client."
     ::= { arrisRouterLanClientEntry 1 }

arrisRouterLanClientIPAddr OBJECT-TYPE
     SYNTAX      InetAddress
     MAX-ACCESS  read-create
     STATUS      current
     DESCRIPTION "Current IP address for the DHCP client.
                  NOTE: This mib has read-create access property only when Comcast use TS9.x loads. Otherwise it is not-accessible."
     ::= { arrisRouterLanClientEntry 2 }

arrisRouterLanClientHostName OBJECT-TYPE
     SYNTAX      DisplayString (SIZE (0..64))
     MAX-ACCESS  read-create
     STATUS      current
     DESCRIPTION "Hostname for the DHCP client."
     ::= { arrisRouterLanClientEntry 3 }

arrisRouterLanClientMAC OBJECT-TYPE
     SYNTAX      MacAddress
     MAX-ACCESS  read-create
     STATUS      current
     DESCRIPTION "MAC address of the DHCP client."
     ::= { arrisRouterLanClientEntry 4 }

arrisRouterLanClientMACMfg OBJECT-TYPE
     SYNTAX DisplayString (SIZE(0..64))
     MAX-ACCESS read-only
     STATUS deprecated
     DESCRIPTION "The manufacturer of the hardware adapter."
     ::= { arrisRouterLanClientEntry 5 }

arrisRouterLanClientAdapterType OBJECT-TYPE
     SYNTAX      INTEGER {  unknown(0),
                            ethernet(1),
                            usb(2),
                            moca(3),
                            dsg(4),
                            wireless1(5),
                            wireless2(6),
                            wireless3(7),
                            wireless4(8),
                            wireless5(9),
                            wireless6(10),
                            wireless7(11),
                            wireless8(12),
                            wireless9(13),
                            wireless10(14),
                            wireless11(15),
                            wireless12(16),
                            wireless13(17),
                            wireless14(18),
                            wireless15(19),
                            wireless16(20),
                            ethernet2(21),
                            ethernet3(22),
                            ethernet4(23)
                            }
     MAX-ACCESS	read-only
     STATUS		current
     DESCRIPTION "The type of the adapter.
                  NOTE: For TS7.x, value 2 represents wireless, NOT usb."
     ::= { arrisRouterLanClientEntry 6 }

arrisRouterLanClientType OBJECT-TYPE
     SYNTAX      INTEGER { unknown(0), dynamic(1), static(5), dynamicReserved(6) }
     MAX-ACCESS  read-only
     STATUS      current
     DESCRIPTION "Type of IP address.  Value list:
                                              1: unknown(0)  ( No client should use this value)
                                              2: dynamic(1)  ( The client IP address is in DHCPv6 or DHCPv6 lease file, but it don't configured as Reserved client on WebGUI)
                                              3: static(5)  (If the client is online, and we can't find the client information in  DHCPv4 or DHCPv6 lease file and it is not configured as Reserved client on WebGUI, then we put it types to static. Notice IPv6 stateless client and link local client would also tagged as this type)
                                              4: dynamic_reserved(6) (The Reserved client configured on WebGUI.)"
     ::= { arrisRouterLanClientEntry 7 }

arrisRouterLanClientLeaseStart OBJECT-TYPE
     SYNTAX      DateAndTime
     MAX-ACCESS  read-only
     STATUS      deprecated
     DESCRIPTION "The time and date when this lease started. For static entries, this is the date/time when the row was created if known or zero."
     ::= { arrisRouterLanClientEntry 8 }

arrisRouterLanClientLeaseEnd OBJECT-TYPE
     SYNTAX      DateAndTime
     MAX-ACCESS  read-only
     STATUS      current
     DESCRIPTION "The time and date when this lease expires.  If arrisRouterLanClientType is static this is meaningless and will return an unspecified date/time."
     ::= { arrisRouterLanClientEntry 9 }

arrisRouterLanClientStatus OBJECT-TYPE
     SYNTAX      INTEGER { down(0), up(1) }
     MAX-ACCESS read-only
     STATUS deprecated
     DESCRIPTION "The status of the IP interface."
     ::= { arrisRouterLanClientEntry 10 }

arrisRouterLanClientInfLease OBJECT-TYPE
     SYNTAX      INTEGER { notApplicable(0), true(1), false(2) }
     MAX-ACCESS read-only
     STATUS deprecated
     DESCRIPTION "Returns true(1) if the lease is infinite, else false(2). This only applies to dynamic leases.  Rows for static items will always return notApplicable(0)."
     ::= { arrisRouterLanClientEntry 11 }

arrisRouterLanClientLeaseState OBJECT-TYPE
     SYNTAX   INTEGER {
                leaseStateAvailable(0),
                leaseStateArping(1),
                leaseStateOffering(2),
                leaseStateUnavailable(3),
                leaseStateReserved(4),
                leaseStateArpBlackListed(5),
                leaseStateInactive(6),
                leaseStateZombie(7)
            }
     MAX-ACCESS read-only
     STATUS deprecated
     DESCRIPTION "Returns lease state."
     ::= { arrisRouterLanClientEntry 12 }

arrisRouterLanClientRowStatus OBJECT-TYPE
     SYNTAX      RowStatus
     MAX-ACCESS  read-create
     STATUS current
     DESCRIPTION "To create or remove static clients.  It is not possible to remove rows that correspond to dynamic IP addresses."
     ::= { arrisRouterLanClientEntry 13 }

arrisRouterLanClientOnline OBJECT-TYPE
     SYNTAX      INTEGER { offline(0), online(1) }
     MAX-ACCESS read-only
     STATUS current
     DESCRIPTION "Returns the if the client is currently online (connected/active) or offline."
     ::= { arrisRouterLanClientEntry 14 }

arrisRouterLanClientComment OBJECT-TYPE
     SYNTAX DisplayString
     MAX-ACCESS read-create
     STATUS current
     DESCRIPTION "Comment field for the client."
     ::= { arrisRouterLanClientEntry 15 }

arrisRouterLanClientCustom OBJECT-TYPE
     SYNTAX      INTEGER { unknown(0), custom(1) }
     MAX-ACCESS read-only
     STATUS current
     DESCRIPTION "Returns whether the client is known in the client table or not."
     ::= { arrisRouterLanClientEntry 16 }

arrisRouterLanClientManufacturerOUI OBJECT-TYPE
     SYNTAX      DisplayString (SIZE (0..6))
     MAX-ACCESS  read-only
     STATUS      current
     DESCRIPTION "Organizationally unique identifier of the Device manufacturer as provided to the Gateway by the Device.
	             Represented as a six hexadecimal-digit value using all upper-case letters and including any leading zeros. Possible patterns:
                     [0-9A-F]{0..6} "
     ::= { arrisRouterLanClientEntry 17 }

arrisRouterLanClientSerialNumber OBJECT-TYPE
     SYNTAX      DisplayString (SIZE (0..64))
     MAX-ACCESS  read-only
     STATUS      current
     DESCRIPTION "Serial number of the Device as provided to the Gateway by the Device."
     ::= { arrisRouterLanClientEntry 18 }

arrisRouterLanClientProductClass OBJECT-TYPE
     SYNTAX      DisplayString (SIZE (0..64))
     MAX-ACCESS  read-only
     STATUS      current
     DESCRIPTION "Identifier of the class of product for which the Device's serial number applies as provided to the Gateway by the Device.
                 If the Device does not provide a Product Class, then this parameter MUST be an empty string."
     ::= { arrisRouterLanClientEntry 19 }

arrisRouterLanClientDeviceName OBJECT-TYPE
     SYNTAX      DisplayString (SIZE (0..64))
     MAX-ACCESS  read-only
     STATUS      current
     DESCRIPTION "Device name."
     ::= { arrisRouterLanClientEntry 20 }

arrisRouterLanClientRSSI OBJECT-TYPE
     SYNTAX      INTEGER
     MAX-ACCESS  read-only
     STATUS      current
     DESCRIPTION "Received signal strength indication."
     ::= { arrisRouterLanClientEntry 21 }

arrisRouterLanClientLinkLocalAddrType OBJECT-TYPE
     SYNTAX      InetAddressType
     MAX-ACCESS  read-only
     STATUS      current
     DESCRIPTION "Current Link Local IP address type for the client."
     ::= { arrisRouterLanClientEntry 22 }

arrisRouterLanClientLinkLocalAddr OBJECT-TYPE
     SYNTAX      InetAddress
     MAX-ACCESS  read-only
     STATUS      current
     DESCRIPTION "Current Link Local IP address for the client."
     ::= { arrisRouterLanClientEntry 23 }

arrisRouterLanClientLastChange OBJECT-TYPE
     SYNTAX     Integer32
     UNITS      "seconds"
     MAX-ACCESS read-only
     STATUS current
     DESCRIPTION "Returns the time from last change state to now."
     ::= { arrisRouterLanClientEntry 24 }

arrisRouterLanClientTimeConnected OBJECT-TYPE
     SYNTAX      Integer32
     UNITS      "seconds"
     MAX-ACCESS  read-only
     STATUS      current
     DESCRIPTION "Returns the time since connected in seconds"
     ::= { arrisRouterLanClientEntry 25 }

-- up/down history for client devices

arrisRouterDeviceUpDownTable OBJECT-TYPE
     SYNTAX      SEQUENCE OF ArrisRouterDeviceUpDownEntry
     MAX-ACCESS  not-accessible
     STATUS      current
     DESCRIPTION
         "This table contains information on when client devices connected to this Router are up and accessible."
     ::= { arrisRouterClientObjects 3 }

arrisRouterDeviceUpDownEntry OBJECT-TYPE
     SYNTAX      ArrisRouterDeviceUpDownEntry
     MAX-ACCESS  not-accessible
     STATUS      current
     DESCRIPTION
         "This table contains information on when client devices connected to this Router are up and accessible."
     INDEX { ifIndex, arrisRouterDeviceUpDownIndex }
     ::= {  arrisRouterDeviceUpDownTable 1 }

ArrisRouterDeviceUpDownEntry ::= SEQUENCE {
         arrisRouterDeviceUpDownIndex		Integer32,
         arrisRouterDeviceUpDownMAC		MacAddress,
         arrisRouterDeviceUpDownIPType		InetAddressType,
         arrisRouterDeviceUpDownIPAddr		InetAddress,
         arrisRouterDeviceUpDownStart		DateAndTime,
         arrisRouterDeviceUpDownEnd		DateAndTime,
         arrisRouterDeviceUpDownStatus		RowStatus
         }


arrisRouterDeviceUpDownIndex OBJECT-TYPE
     SYNTAX      Integer32 (1..30)
     MAX-ACCESS  not-accessible
     STATUS      current
     DESCRIPTION
         "Index used to order the arrisRouterClientsUpDownTable entries."
     ::= { arrisRouterDeviceUpDownEntry 1 }

arrisRouterDeviceUpDownMAC OBJECT-TYPE
     SYNTAX      MacAddress
     MAX-ACCESS  read-only
     STATUS      current
     DESCRIPTION "MAC address of the client.  This is used to index the table."
     ::= { arrisRouterDeviceUpDownEntry 2 }

arrisRouterDeviceUpDownIPType OBJECT-TYPE
     SYNTAX      InetAddressType
     MAX-ACCESS  read-only
     STATUS      current
     DESCRIPTION "The IP address type for the client during the time period specified by this row."
     ::= { arrisRouterDeviceUpDownEntry 3 }

arrisRouterDeviceUpDownIPAddr OBJECT-TYPE
     SYNTAX      InetAddress
     MAX-ACCESS  read-only
     STATUS      current
     DESCRIPTION "The IP address for the client during the time period specified by this row."
     ::= { arrisRouterDeviceUpDownEntry 4 }

arrisRouterDeviceUpDownStart OBJECT-TYPE
     SYNTAX      DateAndTime
     MAX-ACCESS  read-only
     STATUS      current
     DESCRIPTION
         "Time when this client device is 'detected' to be 'UP' and accessible."
     ::= { arrisRouterDeviceUpDownEntry 5 }

arrisRouterDeviceUpDownEnd OBJECT-TYPE
     SYNTAX      DateAndTime
     MAX-ACCESS  read-only
     STATUS      current
     DESCRIPTION "Time when this client device is 'detected' to NOT be 'UP' and accessible."
     ::= { arrisRouterDeviceUpDownEntry 6 }

arrisRouterDeviceUpDownStatus OBJECT-TYPE
     SYNTAX      RowStatus
     MAX-ACCESS  read-create
     STATUS      current
     DESCRIPTION "This is ONLY used to remove rows/items from this table."
     ::= { arrisRouterDeviceUpDownEntry 7 }


arrisRouterLanCustomCount OBJECT-TYPE
     SYNTAX      Unsigned32
     MAX-ACCESS  read-only
     STATUS      current
     DESCRIPTION "Current count of custom mapping of LAN clients to friendly names and other attributes.  This corresponds to the number of rows in arrisRouterLanClientCustomTable."
     ::= { arrisRouterClientObjects 4 }


-- This table supports up to 25 devices.

arrisRouterLanCustomTable OBJECT-TYPE
      SYNTAX      SEQUENCE OF ArrisRouterLanCustomEntry
      MAX-ACCESS  not-accessible
      STATUS      current
      DESCRIPTION "Table contains the set of mapping of LAN clients to friendly names and other attributes.
                    The table can be used to look up clients by IP address or MAC address or both.
                    The only field the system will fill-in automaticaly is arrisRouterLanCustomMACMfg."
      ::= { arrisRouterClientObjects 5 }

arrisRouterLanCustomEntry OBJECT-TYPE
      SYNTAX      ArrisRouterLanCustomEntry
      MAX-ACCESS  not-accessible
      STATUS      current
      DESCRIPTION "Table contains the set of mapping of LAN clients to friendly names and other attributes.
                    The table can be used to look up clients by IP address or MAC address or both.
                    The only field the system will fill-in automaticaly is arrisRouterLanCustomMACMfg."
      INDEX { arrisRouterLanCustomIdx }
      ::= { arrisRouterLanCustomTable 1 }

ArrisRouterLanCustomEntry ::= SEQUENCE {
        arrisRouterLanCustomIdx			Unsigned32,
        arrisRouterLanCustomMAC			MacAddress,
        arrisRouterLanCustomIPAddrType		InetAddressType,
        arrisRouterLanCustomIPAddr		InetAddress,
        arrisRouterLanCustomFriendName		DisplayString,
        arrisRouterLanCustomHostName		DisplayString,
        arrisRouterLanCustomMACMfg		DisplayString,
        arrisRouterLanCustomComments		DisplayString,
        arrisRouterLanCustomRowStatus		RowStatus
        }

arrisRouterLanCustomIdx OBJECT-TYPE
     SYNTAX      Unsigned32
     MAX-ACCESS  not-accessible
     STATUS      current
     DESCRIPTION "Index."
     ::= { arrisRouterLanCustomEntry 1 }

arrisRouterLanCustomMAC OBJECT-TYPE
     SYNTAX      MacAddress
     MAX-ACCESS  read-create
     STATUS      current
     DESCRIPTION "MAC address of the client.  This is used to index the table."
     ::= { arrisRouterLanCustomEntry 2 }

arrisRouterLanCustomIPAddrType OBJECT-TYPE
     SYNTAX      InetAddressType
     MAX-ACCESS  read-create
     STATUS      current
     DESCRIPTION "The IP address.  This is optional but either the IP or MAC should be present."
     ::= { arrisRouterLanCustomEntry 3 }

arrisRouterLanCustomIPAddr OBJECT-TYPE
     SYNTAX      InetAddress
     MAX-ACCESS  read-create
     STATUS      current
     DESCRIPTION "The IP address.  This is optional but either the IP or MAC should be present."
     ::= { arrisRouterLanCustomEntry 4 }

arrisRouterLanCustomFriendName OBJECT-TYPE
     SYNTAX      DisplayString (SIZE(0..64))
     MAX-ACCESS  read-create
     STATUS      current
     DESCRIPTION "The 'friendly' name for this client.  The default is the host name.
                  Users can edit this via a user interface."
     ::= { arrisRouterLanCustomEntry 5 }

arrisRouterLanCustomHostName OBJECT-TYPE
     SYNTAX      DisplayString (SIZE(0..64))
     MAX-ACCESS  read-create
     STATUS      current
     DESCRIPTION "Hostname for the client."
     ::= { arrisRouterLanCustomEntry 6 }

arrisRouterLanCustomMACMfg OBJECT-TYPE
     SYNTAX DisplayString (SIZE(0..64))
     MAX-ACCESS read-only
     STATUS current
     DESCRIPTION "The manufacturer of the hardware adapter."
     ::= { arrisRouterLanCustomEntry 7 }

arrisRouterLanCustomComments OBJECT-TYPE
     SYNTAX DisplayString
     MAX-ACCESS read-create
     STATUS current
     DESCRIPTION "Additional comments."
     ::= { arrisRouterLanCustomEntry 8 }

arrisRouterLanCustomRowStatus OBJECT-TYPE
      SYNTAX     RowStatus
      MAX-ACCESS read-create
      STATUS     current
      DESCRIPTION
		  "Set to true(1) to remove this device from the list/table."
      ::= { arrisRouterLanCustomEntry 9 }

arrisRouterLanCurrentClientTable OBJECT-TYPE
      SYNTAX      SEQUENCE OF ArrisRouterLanCurrentClientEntry
      MAX-ACCESS  not-accessible
      STATUS      current
      DESCRIPTION "This table contains all current client devices on the LAN.
                  This primarily includes LAN devices that use DHCP to request their IP address from the Gateway device.
                  This table also includes any device that has been statically configured with an IP address on the same subnet as the Gateway device.
                  These devices are usually discovered through ARP.
                  This table also includes any device that has been added to the arrisRouterLanStaticClientTable."
      ::= { arrisRouterClientObjects 6 }

arrisRouterLanCurrentClientEntry OBJECT-TYPE
      SYNTAX      ArrisRouterLanCurrentClientEntry
      MAX-ACCESS  not-accessible
      STATUS      current
      DESCRIPTION "Entry in the arrisRouterLanCurrentClientTable."
      INDEX { ifIndex, arrisRouterLanCurrentClientIndex }
      ::= { arrisRouterLanCurrentClientTable 1 }

ArrisRouterLanCurrentClientEntry ::= SEQUENCE {
        arrisRouterLanCurrentClientIndex            Integer32,
        arrisRouterLanCurrentClientIPAddrType       InetAddressType,
        arrisRouterLanCurrentClientIPAddr           InetAddress,
        arrisRouterLanCurrentClientIPAddrTextual    DisplayString,
        arrisRouterLanCurrentClientHostName         DisplayString,
        arrisRouterLanCurrentClientMAC              MacAddress,
        arrisRouterLanCurrentClientMACMfg           DisplayString,
        arrisRouterLanCurrentClientAdapterType      INTEGER,
        arrisRouterLanCurrentClientType             INTEGER,
        arrisRouterLanCurrentClientLeaseStart       DateAndTime,
        arrisRouterLanCurrentClientLeaseEnd         DateAndTime,
        arrisRouterLanCurrentClientStatus           INTEGER,
        arrisRouterLanCurrentClientInfLease         INTEGER,
        arrisRouterLanCurrentClientLeaseState       INTEGER,
        arrisRouterLanCurrentClientFirstSeen        DateAndTime,
        arrisRouterLanCurrentClientLastSeen         DateAndTime,
        arrisRouterLanCurrentClientConnectionInfo   DisplayString,
        arrisRouterLanCurrentClientLeaseTime        Integer32
        }

arrisRouterLanCurrentClientIndex OBJECT-TYPE
     SYNTAX      Integer32 (1..64)
     MAX-ACCESS  not-accessible
     STATUS      current
     DESCRIPTION "Index for the table."
     ::= { arrisRouterLanCurrentClientEntry 1 }

arrisRouterLanCurrentClientIPAddrType OBJECT-TYPE
     SYNTAX      InetAddressType
     MAX-ACCESS  read-only
     STATUS      current
     DESCRIPTION "Current IP address type for the client device."
     ::= { arrisRouterLanCurrentClientEntry 2 }

arrisRouterLanCurrentClientIPAddr OBJECT-TYPE
     SYNTAX      InetAddress
     MAX-ACCESS  read-only
     STATUS      current
     DESCRIPTION "Current IP address for the client device."
     ::= { arrisRouterLanCurrentClientEntry 3 }

arrisRouterLanCurrentClientIPAddrTextual OBJECT-TYPE
     SYNTAX      DisplayString
     MAX-ACCESS  read-only
     STATUS      current
     DESCRIPTION "A human-readable textual representation of the arrisRouterLanCurrentClientIPAddr."
     ::= { arrisRouterLanCurrentClientEntry 4 }

arrisRouterLanCurrentClientHostName OBJECT-TYPE
     SYNTAX      DisplayString (SIZE (0..64))
     MAX-ACCESS  read-only
     STATUS      current
     DESCRIPTION "Hostname for the client."
     ::= { arrisRouterLanCurrentClientEntry 5 }

arrisRouterLanCurrentClientMAC OBJECT-TYPE
     SYNTAX      MacAddress
     MAX-ACCESS  read-only
     STATUS      current
     DESCRIPTION "MAC address of the client."
     ::= { arrisRouterLanCurrentClientEntry 6 }

arrisRouterLanCurrentClientMACMfg OBJECT-TYPE
     SYNTAX DisplayString (SIZE(0..64))
     MAX-ACCESS read-only
     STATUS current
     DESCRIPTION "The manufacturer of the hardware adapter."
     ::= { arrisRouterLanCurrentClientEntry 7 }

arrisRouterLanCurrentClientAdapterType OBJECT-TYPE
     SYNTAX      INTEGER { unknown(0), ethernet(1), wireless(2), moca(3) }
     MAX-ACCESS	read-only
     STATUS		current
     DESCRIPTION "The type of the adapter."
     ::= { arrisRouterLanCurrentClientEntry 8 }

arrisRouterLanCurrentClientType OBJECT-TYPE
     SYNTAX      INTEGER { unknown(0), dynamic(1), staticDiscover(2), staticConfigure(3) }
     MAX-ACCESS  read-only
     STATUS      current
     DESCRIPTION "Type of client.  DHCP clients are dynamic.
                  Clients that have been statically configured on the device and are discovered via ARP are staticDiscover.
                  Clients that have been configured in the arrisRouterLanStaticClientTable are staticConfigure."
     ::= { arrisRouterLanCurrentClientEntry 9 }

arrisRouterLanCurrentClientLeaseStart OBJECT-TYPE
     SYNTAX      DateAndTime
     MAX-ACCESS  read-only
     STATUS      current
     DESCRIPTION "The time and date when this lease started. This only applies to clients where arrisRouterLanCurrentClientType equals dynamic(1)"
     ::= { arrisRouterLanCurrentClientEntry 10 }

arrisRouterLanCurrentClientLeaseEnd OBJECT-TYPE
     SYNTAX      DateAndTime
     MAX-ACCESS  read-only
     STATUS      current
     DESCRIPTION "The time and date when this lease expires. This only applies to clients where arrisRouterLanCurrentClientType equals dynamic(1)"
     ::= { arrisRouterLanCurrentClientEntry 11 }

arrisRouterLanCurrentClientStatus OBJECT-TYPE
     SYNTAX      INTEGER { unknown(-1), down(0), up(1) }
     MAX-ACCESS read-only
     STATUS current
     DESCRIPTION "The most recent known status of the LAN client."
     ::= { arrisRouterLanCurrentClientEntry 12 }

arrisRouterLanCurrentClientInfLease OBJECT-TYPE
     SYNTAX      INTEGER { notApplicable(0), true(1), false(2) }
     MAX-ACCESS read-only
     STATUS current
     DESCRIPTION "Returns true(1) if the lease is infinite, else false(2). This only applies to clients where arrisRouterLanCurrentClientType equals dynamic(1)"
     ::= { arrisRouterLanCurrentClientEntry 13 }

arrisRouterLanCurrentClientLeaseState OBJECT-TYPE
     SYNTAX   INTEGER {
                leaseStateAvailable(0),
                leaseStateArping(1),
                leaseStateOffering(2),
                leaseStateUnavailable(3),
                leaseStateReserved(4),
                leaseStateArpBlackListed(5),
                leaseStateInactive(6),
                leaseStateZombie(7)
            }
     MAX-ACCESS read-only
     STATUS current
     DESCRIPTION "Returns the state of the lease. This only applies to clients where arrisRouterLanCurrentClientType equals dynamic(1).
                Any static client will return 'leaseStateUnavailable'"
     ::= { arrisRouterLanCurrentClientEntry 14 }

arrisRouterLanCurrentClientFirstSeen OBJECT-TYPE
     SYNTAX      DateAndTime
     MAX-ACCESS read-only
     STATUS current
     DESCRIPTION "The time, if known, when this client was first seen.
                For 'dynamic' clients, this will usually be when the first DHCP lease was given out to this client since the last boot.
                This value will not necessarily match arrisRouterLanCurrentClientLeaseStart as several DHCP renewals may have occurred.
                For 'staticDiscover' clients, this value will match the time of the first ARP response since the last boot.
                For 'staticConfigure' clients, this value will match the time of the first ARP response since the last boot."
     ::= { arrisRouterLanCurrentClientEntry 15 }

arrisRouterLanCurrentClientLastSeen OBJECT-TYPE
     SYNTAX      DateAndTime
     MAX-ACCESS read-only
     STATUS current
     DESCRIPTION "The time, if known, when this client was most recently (last) seen.
                  If the device has been disconnected or powered off this value will reflect that.
                  If the device is currently active, this value should match the current system time with a variability of up to 1 minute."
     ::= { arrisRouterLanCurrentClientEntry 16 }

arrisRouterLanCurrentClientConnectionInfo OBJECT-TYPE
     SYNTAX      DisplayString
     MAX-ACCESS read-only
     STATUS current
     DESCRIPTION "This value returns a string that may contain additional connection details.
                    For Ethernet clients, this may return the connection port and connection speed.
                    For Wireless clients, this may return brief details about the wireless connection.
                    This field may also be blank and is only for informational purposes."
     ::= { arrisRouterLanCurrentClientEntry 17 }

arrisRouterLanCurrentClientLeaseTime OBJECT-TYPE
     SYNTAX      Integer32
     UNITS       "Seconds"
     MAX-ACCESS read-only
     STATUS current
     DESCRIPTION "The length of the DHCP lease in seconds.  For static LAN clients, this value will be zero."
     ::= { arrisRouterLanCurrentClientEntry 18 }

-- LAN Static client table

arrisRouterLanStaticClientTable OBJECT-TYPE
      SYNTAX      SEQUENCE OF ArrisRouterLanStaticClientEntry
      MAX-ACCESS  not-accessible
      STATUS      current
      DESCRIPTION "This table contains devices that are statically configured to maintain the same IP address between reboots."
      ::= { arrisRouterClientObjects 7 }

arrisRouterLanStaticClientEntry OBJECT-TYPE
      SYNTAX      ArrisRouterLanStaticClientEntry
      MAX-ACCESS  not-accessible
      STATUS      current
      DESCRIPTION "Entry in the arrisRouterLanStaticClientTable."
      INDEX { ifIndex, arrisRouterLanStaticClientIndex }
      ::= { arrisRouterLanStaticClientTable 1 }

ArrisRouterLanStaticClientEntry ::= SEQUENCE {
        arrisRouterLanStaticClientIndex            Integer32,
        arrisRouterLanStaticClientIPAddrType       InetAddressType,
        arrisRouterLanStaticClientIPAddr           InetAddress,
        arrisRouterLanStaticClientHostName         DisplayString,
        arrisRouterLanStaticClientMAC              MacAddress,
        arrisRouterLanStaticClientRowStatus        RowStatus
        }

arrisRouterLanStaticClientIndex OBJECT-TYPE
     SYNTAX      Integer32 (1..16)
     MAX-ACCESS  not-accessible
     STATUS      current
     DESCRIPTION "Index for the table."
     ::= { arrisRouterLanStaticClientEntry 1 }

arrisRouterLanStaticClientIPAddrType OBJECT-TYPE
     SYNTAX      InetAddressType
     MAX-ACCESS  read-create
     STATUS      current
     DESCRIPTION "The type of the statically configured IP address."
     ::= { arrisRouterLanStaticClientEntry 2 }

arrisRouterLanStaticClientIPAddr OBJECT-TYPE
     SYNTAX      InetAddress
     MAX-ACCESS  read-create
     STATUS      current
     DESCRIPTION "The IP addres to statically associate with this device."
     ::= { arrisRouterLanStaticClientEntry 3 }

arrisRouterLanStaticClientHostName OBJECT-TYPE
     SYNTAX      DisplayString (SIZE (0..64))
     MAX-ACCESS  read-create
     STATUS      current
     DESCRIPTION "An optional hostname for the client device."
     ::= { arrisRouterLanStaticClientEntry 4 }

arrisRouterLanStaticClientMAC OBJECT-TYPE
     SYNTAX      MacAddress
     MAX-ACCESS  read-create
     STATUS      current
     DESCRIPTION "The MAC address of the client device."
     ::= { arrisRouterLanStaticClientEntry 5 }

arrisRouterLanStaticClientRowStatus OBJECT-TYPE
     SYNTAX      RowStatus
     MAX-ACCESS  read-create
     STATUS      current
     DESCRIPTION "The status of the row."
     ::= { arrisRouterLanStaticClientEntry 6 }

-- ---------------------------------------------------------------------
-- LAN Client Table extension for DHCP Options
-- ---------------------------------------------------------------------

arrisRouterLanClientDHCPOptionsTable OBJECT-TYPE
      SYNTAX      SEQUENCE OF ArrisRouterLanClientDHCPOptionsEntry
      MAX-ACCESS  not-accessible
      STATUS      current
      DESCRIPTION "Table contains the set of DHCP clients for this Lan."
      ::= { arrisRouterClientObjects 8 }

arrisRouterLanClientDHCPOptionsEntry OBJECT-TYPE
      SYNTAX      ArrisRouterLanClientDHCPOptionsEntry
      MAX-ACCESS  not-accessible
      STATUS      current
      DESCRIPTION "Table contains the set of DHCP clients for this Lan."
      INDEX { ifIndex, arrisRouterLanClientIPAddrType, arrisRouterLanClientIPAddr, arrisRouterLanClientDHCPOptionsIdx }
      ::= { arrisRouterLanClientDHCPOptionsTable 1 }

ArrisRouterLanClientDHCPOptionsEntry ::= SEQUENCE {
        arrisRouterLanClientDHCPOptionsIdx          Unsigned32,
        arrisRouterLanClientDHCPOptionsTag          Unsigned32,
        arrisRouterLanClientDHCPOptionsValue        DisplayString,
        arrisRouterLanClientDHCPOptionsRowStatus    RowStatus
        }

arrisRouterLanClientDHCPOptionsIdx OBJECT-TYPE
     SYNTAX      Unsigned32 (1..4)
     MAX-ACCESS  not-accessible
     STATUS      current
     DESCRIPTION "Table index"
     ::= { arrisRouterLanClientDHCPOptionsEntry 1 }

arrisRouterLanClientDHCPOptionsTag OBJECT-TYPE
     SYNTAX      Unsigned32 (1..254)
     MAX-ACCESS  read-only
     STATUS      current
     DESCRIPTION "DHCP Option Number"
     ::= { arrisRouterLanClientDHCPOptionsEntry 2 }

arrisRouterLanClientDHCPOptionsValue OBJECT-TYPE
     SYNTAX DisplayString (SIZE(0..64))
     MAX-ACCESS read-only
     STATUS current
     DESCRIPTION "DHCP Option Value."
     ::= { arrisRouterLanClientDHCPOptionsEntry 3 }

arrisRouterLanClientDHCPOptionsRowStatus OBJECT-TYPE
     SYNTAX      RowStatus
     MAX-ACCESS  read-create
     STATUS      current
     DESCRIPTION "RowStatus used to add or remove DHCP Options row entries"
     ::= { arrisRouterLanClientDHCPOptionsEntry 4 }


-- RIP settings

arrisRouterRIPObjects		OBJECT IDENTIFIER ::= { arrisRouterLanConfig 5 }

arrisRouterRIPEnable OBJECT-TYPE
     SYNTAX      TruthValue
     MAX-ACCESS  read-write
     STATUS      current
     DESCRIPTION "Enable/disable RIP authentication."
     ::= { arrisRouterRIPObjects 1 }

arrisRouterRIPAuthEnable OBJECT-TYPE
     SYNTAX      INTEGER { unknown(-1), disable(0), textAuth(1), md5Auth(2) }
     MAX-ACCESS  read-write
     STATUS      current
     DESCRIPTION "Enable/disable RIP authentication and type."
     DEFVAL	{ disable }
     ::= { arrisRouterRIPObjects 2 }

arrisRouterRIPReportTime OBJECT-TYPE
     SYNTAX      Unsigned32
     UNITS		 "seconds"
     MAX-ACCESS  read-write
     STATUS      current
     DESCRIPTION "RIP reporting interval."
     DEFVAL  { 30 }
     ::= { arrisRouterRIPObjects 3 }

arrisRouterRIPAuthKeyString OBJECT-TYPE
     SYNTAX      DisplayString (SIZE(0..16))
     MAX-ACCESS  read-write
     STATUS      current
     DESCRIPTION "RIP authentication key."
     ::= { arrisRouterRIPObjects 4 }

arrisRouterRIPAuthKeyID OBJECT-TYPE
     SYNTAX      Integer32 (0..255)
     MAX-ACCESS  read-write
     STATUS      current
     DESCRIPTION "RIP authentication key identifier."
     ::= { arrisRouterRIPObjects 5 }

arrisRouterRIPIPAddrType OBJECT-TYPE
     SYNTAX      InetAddressType
     MAX-ACCESS  read-write
     STATUS      current
     DESCRIPTION "RIP destination IP address type."
     ::= { arrisRouterRIPObjects 6 }

arrisRouterRIPIPAddr OBJECT-TYPE
     SYNTAX      InetAddress
     MAX-ACCESS  read-write
     STATUS      current
     DESCRIPTION "RIP unicast reporting destination IP address.
                  If this is configured to an ip address other than 0.0.0.0,
                  then the RIP messaging ( which is generally multicasted upstream ) will be unicasted to this ip address."
     ::= { arrisRouterRIPObjects 7 }

arrisRouterRIPPrefixLen OBJECT-TYPE
     SYNTAX      InetAddressPrefixLength
     MAX-ACCESS  read-write
     STATUS      current
     DESCRIPTION "The prefix for the routed subnet. This value can be set or the value: arrisRouterRIPSubnetMask.
                  For additional details see the description for: arrisRouterRIPRoutedNetIP."
     ::= { arrisRouterRIPObjects 8 }

arrisRouterRIPAuthKeyChain OBJECT-TYPE
     SYNTAX      DisplayString (SIZE(0..64))
     MAX-ACCESS  read-write
     STATUS      current
     DESCRIPTION "RIP authentication key chain."
     ::= { arrisRouterRIPObjects 9 }

arrisRouterRIPRoutedSubnetIPType OBJECT-TYPE
     SYNTAX      InetAddressType
     MAX-ACCESS  read-write
     STATUS      current
     DESCRIPTION "The IP address type for arrisRouterRIPRoutedNetIP."
     ::= { arrisRouterRIPObjects 10 }

arrisRouterRIPRoutedSubnetIP OBJECT-TYPE
     SYNTAX      InetAddress
     MAX-ACCESS  read-write
     STATUS      current
     DESCRIPTION "The specific network in the configured subnet that will be adverstised and routed.
                This feature allows for the configuration of a public LAN-side subnet of hosts which is not necessarily
                on the same subnet as the CMTS HFC IP address(s), CM IP address, or WAN-MAN IP address subnet.
                The CPEs belonging to this routed subnet will have their IP addresses assigned statically.
                The default gateway for these CPEs will be one of the addresses in the configured subnet.
                The gateway IP address specified will become an actual secondary IP address on the device.
                This secondary IP address will be share a single private LAN interface mac address; that is,
                there will be (2) IP address on a single stack. (192.168.0.1 and arrisRouterRIPSubnetGWNetIP).
                The device will also send RIP messages upstream to the CMTS router advertising this LAN-side routed
                subnet so when frames come into the CMTS router destined to this routed subnet network,
                the CMTS router will know how to route those frames."
     ::= { arrisRouterRIPObjects 11 }

arrisRouterRIPRoutedSubnetGWNetIPType OBJECT-TYPE
     SYNTAX      InetAddressType
     MAX-ACCESS  read-write
     STATUS      current
     DESCRIPTION "The IP address type for arrisRouterRIPRoutedNetIP.
                  NOTE: For TS7.x, this mib has NO default value."
     DEFVAL { ipv4 }
     ::= { arrisRouterRIPObjects 12 }

arrisRouterRIPRoutedSubnetGWNetIP OBJECT-TYPE
     SYNTAX      InetAddress
     MAX-ACCESS  read-write
     STATUS      current
     DESCRIPTION "See the description of arrisRouterRIPRoutedNetIP.  This is the Gateway IP address for the routable subnet."
     ::= { arrisRouterRIPObjects 13 }

arrisRouterRIPRoutedSubnetMask OBJECT-TYPE
     SYNTAX      InetAddress
     MAX-ACCESS  read-write
     STATUS      current
     DESCRIPTION "The subnet mask used for the routed subnet.  This value will match arrisRouterRIPPrefixLen.
                    Usually prefixes are used with IPv6 and Netmasks are used with IPv4."
     ::= { arrisRouterRIPObjects 14 }

arrisRouterRIPRoutedSubnetEnabled OBJECT-TYPE
     SYNTAX      TruthValue
     MAX-ACCESS  read-write
     STATUS      current
     DESCRIPTION "If this is enabled, then we will advertise the RIP routed subnet network IP address with the next hop as the CM IP address."
     ::= { arrisRouterRIPObjects 15 }

arrisRouterRIPSendCMInterface OBJECT-TYPE
     SYNTAX      TruthValue
     MAX-ACCESS  read-write
     STATUS      current
     DESCRIPTION "If this is true/enabled, then RIP advertisements will be sent via the CM IP interface.
                If this is false/disabled then RIP advertisements will be sent via the eRouter WAN IP interface."
     DEFVAL { false }
     ::= { arrisRouterRIPObjects 16 }

arrisRouterRIPRoutedSubnetDHCP OBJECT-TYPE
     SYNTAX      TruthValue
     MAX-ACCESS  read-write
     STATUS      current
     DESCRIPTION "If this is true/enabled, then a DHCP server will be started on the device for the routed subnet.
                If this is false/disabled then the DHCP server will not be started and all LAN-based CPE devices
                will need to be assigned static IP addresses."
     DEFVAL { false }
     ::= { arrisRouterRIPObjects 17 }

arrisRouterRIPRoutedSubnetNAT OBJECT-TYPE
     SYNTAX      TruthValue
     MAX-ACCESS  read-write
     STATUS      current
     DESCRIPTION "If this is true/enabled, then a the Routed Subnet will be NATed using the Gateway Ip Address
                If this is false/disabled then the NAT will be disabled for the routed subnet."
     DEFVAL { false }
     ::= { arrisRouterRIPObjects 18 }

arrisRouterRIPSendVersion OBJECT-TYPE
     SYNTAX DisplayString (SIZE(0..8))
     MAX-ACCESS  read-write
     STATUS      current
     DESCRIPTION "RIP version to send.{0:UNSPEC, 1:RIPV1, 2M:RIPV2 MULTICAST, 2B:RIPV2 BROADCAST}"
     ::= { arrisRouterRIPObjects 20 }

arrisRouterRIPReceiveVersion OBJECT-TYPE
     SYNTAX      INTEGER
     MAX-ACCESS  read-write
     STATUS      current
     DESCRIPTION "RIP version to receive."
     ::= { arrisRouterRIPObjects 21 }

arrisRouterRIPDefaultMetric OBJECT-TYPE
     SYNTAX      INTEGER
     MAX-ACCESS  read-write
     STATUS      current
     DESCRIPTION "RIP default Metric."
     ::= { arrisRouterRIPObjects 22 }

arrisRouterRIPInterface OBJECT-TYPE
     SYNTAX      INTEGER { ethernet(0), cable(1) }
     MAX-ACCESS  read-write
     STATUS      current
     DESCRIPTION "Interface for RIP."
     ::= { arrisRouterRIPObjects 23 }

arrisRouterRIPRoutedExtSubnetTable OBJECT-TYPE
     SYNTAX      SEQUENCE OF ArrisRouterRIPRoutedExtSubnetEntry
     MAX-ACCESS  not-accessible
     STATUS      current
     DESCRIPTION "Table contains information for external RIPRoutedSubnet"
     ::= { arrisRouterRIPObjects 24 }

arrisRouterRIPRoutedExtSubnetEntry OBJECT-TYPE
     SYNTAX      ArrisRouterRIPRoutedExtSubnetEntry
     MAX-ACCESS  not-accessible
     STATUS      current
     DESCRIPTION "Table contains information for external RIPRoutedSubnet."
     INDEX { ifIndex }  --from IF-MIB
     ::= { arrisRouterRIPRoutedExtSubnetTable 1 }

ArrisRouterRIPRoutedExtSubnetEntry ::= SEQUENCE {
     arrisRouterRipRoutedExtSubnetIdx          Unsigned32,
     arrisRouterRIPRoutedExtSubnetIPType        InetAddressType,
     arrisRouterRIPRoutedExtSubnetIP            InetAddress,
     arrisRouterRIPRoutedExtSubnetGWNetIPType   InetAddressType,
     arrisRouterRIPRoutedExtSubnetGWNetIP       InetAddress,
     arrisRouterRIPRoutedExtSubnetMask      InetAddress,
     arrisRouterRIPRoutedExtSubnetEnabled   TruthValue,
     arrisRouterRIPExtSendCMInterface       TruthValue,
     arrisRouterRIPRoutedExtSubnetDHCP      TruthValue,
     arrisRouterRIPRoutedExtSubnetNAT       TruthValue
}
arrisRouterRipRoutedExtSubnetIdx OBJECT-TYPE
     SYNTAX      Unsigned32 (1..6)
     MAX-ACCESS  not-accessible
     STATUS      current
     DESCRIPTION "Table index"
     ::= { arrisRouterRIPRoutedExtSubnetEntry 1 }

arrisRouterRIPRoutedExtSubnetIPType OBJECT-TYPE
     SYNTAX      InetAddressType
     MAX-ACCESS  read-write
     STATUS      current
     DESCRIPTION "The IP address type for arrisRouterRIPRoutedNetIP"
     ::= { arrisRouterRIPRoutedExtSubnetEntry 2 }

arrisRouterRIPRoutedExtSubnetIP OBJECT-TYPE
     SYNTAX      InetAddress
     MAX-ACCESS  read-write
     STATUS      current
     DESCRIPTION "The specific network in the configured subnet that will be adverstised and routed.
                                This feature allows for the configuration of a public LAN-side subnet of hosts which is not necessarily
                                on the same subnet as the CMTS HFC IP address(s), CM IP address, or WAN-MAN IP address subnet.
                                The CPEs belonging to this routed subnet will have their IP addresses assigned statically.
                                The default gateway for these CPEs will be one of the addresses in the configured subnet.
                                The gateway IP address specified will become an actual secondary IP address on the device.
                                This secondary IP address will be share a single private LAN interface mac address; that is,
                                there will be (2) IP address on a single stack. (192.168.0.1 and arrisRouterRIPSubnetGWNetIP).
                                The device will also send RIP messages upstream to the CMTS router advertising this LAN-side routed
                                subnet so when frames come into the CMTS router destined to this routed subnet network,
                                the CMTS router will know how to route those frames."
     ::= { arrisRouterRIPRoutedExtSubnetEntry 3 }

     arrisRouterRIPRoutedExtSubnetGWNetIPType OBJECT-TYPE
     SYNTAX      InetAddressType
     MAX-ACCESS  read-write
     STATUS      current
     DESCRIPTION "The IP address type for arrisRouterRIPRoutedNetIP"
     DEFVAL { ipv4 }
     ::= { arrisRouterRIPRoutedExtSubnetEntry 4 }

arrisRouterRIPRoutedExtSubnetGWNetIP OBJECT-TYPE
     SYNTAX      InetAddress
     MAX-ACCESS  read-write
     STATUS      current
         DESCRIPTION "See the description of arrisRouterRIPRoutedNetIP.  This is the Gateway IP address for the routable subnet."
     ::= { arrisRouterRIPRoutedExtSubnetEntry 5 }

arrisRouterRIPRoutedExtSubnetMask OBJECT-TYPE
     SYNTAX      InetAddress
     MAX-ACCESS  read-write
     STATUS      current
     DESCRIPTION "The subnet mask used for the routed subnet.  This value will match arrisRouterRIPPrefixLen.
                                        Usually prefixes are used with IPv6 and Netmasks are used with IPv4."
     ::= { arrisRouterRIPRoutedExtSubnetEntry 6 }

arrisRouterRIPRoutedExtSubnetEnabled OBJECT-TYPE
     SYNTAX      TruthValue
     MAX-ACCESS  read-write
     STATUS      current
     DESCRIPTION "If this is enabled, then we will advertise the RIP routed subnet network IP address with the next hop as the CM IP address."
     ::= { arrisRouterRIPRoutedExtSubnetEntry 7 }

     arrisRouterRIPExtSendCMInterface OBJECT-TYPE
     SYNTAX      TruthValue
     MAX-ACCESS  read-write
     STATUS      current
     DESCRIPTION "If this is true/enabled, then RIP advertisements will be sent via the CM IP interface.
                                If this is false/disabled then RIP advertisements will be sent via the eRouter WAN IP interface."
         DEFVAL { false }
     ::= { arrisRouterRIPRoutedExtSubnetEntry 8 }

arrisRouterRIPRoutedExtSubnetDHCP OBJECT-TYPE
     SYNTAX      TruthValue
     MAX-ACCESS  read-write
     STATUS      current
     DESCRIPTION "If this is true/enabled, then a DHCP server will be started on the device for the routed subnet.
                                If this is false/disabled then the DHCP server will not be started and all LAN-based CPE devices
                                will need to be assigned static IP addresses."
         DEFVAL { false }
     ::= { arrisRouterRIPRoutedExtSubnetEntry 9 }

arrisRouterRIPRoutedExtSubnetNAT OBJECT-TYPE
     SYNTAX      TruthValue
     MAX-ACCESS  read-write
     STATUS      current
     DESCRIPTION "If this is true/enabled, then a the Routed Subnet will be NATed using the Gateway Ip Address
                                If this is false/disabled then the NAT will be disabled for the routed subnet."
         DEFVAL { false }
     ::= { arrisRouterRIPRoutedExtSubnetEntry 10 }

-- NOTE: Setup static routes using RFC4292 or at a minimum RFC 1213/1354

arrisRouterLanSettings OBJECT-TYPE
    SYNTAX      INTEGER (1..23)
    MAX-ACCESS  read-write
    STATUS      current
    DESCRIPTION "This always returns doNothing(0) when read.
		-------------Media GW-------------------------
		doNothing(0), applyPrimaryLan(1), applyGuestLans(2), applyAllLans(3), revertSettings(10), resetDefaults(11), restartWLAN(12), resetDefaults6(13).
		This applies settings for the primary LAN - Ethernet and Primary WiFI - if applyPrimaryLan(1) is used.  The network will be restarted.
		This applies settings for all of the guest wireless networks.  The network(s) will be restarted and thus connections to these networks
		will be lost.
		To apply all settings for all networks use applyAllLans(3).
		If applySettings fails, the modified settings will still be in the 'cache' until the device is rebooted or revertSettings(10) is used.
		If several modifications have been made, to revert the settings back to the values stored in the non-volatile store, use revertSettings(10).
		Reset all values in arrisRouterLanTable and arrisRouterWirelessCfg to their defaults by setting this value to resetDefaults(11).
		Restart the Wireless LAN only (12).
		-------------Telephone GW---------------------
		doNothing(0), applyLan1(1), applyLan2(2), applyLan3(3), applyLan4(4), applyLan5(5), applyLan6(6), applyLan7(7), applyLan8(8),
		applyAllLans(20), revertSettings(21), resetDefaults(22), restartWLAN(23)
		Modify arrisRouterLanTable, arrisRouterRIPTable, and arrisRouterWirelessCfg and then set this value to applySettings(1) to apply the settings.
		If applySettings fails, the modified settings will still be in the 'cache' until the device is rebooted or revertSettings(2) is used.
		If several modifications have been made, to revert the settings back to the values stored in the non-volatile store, use revertSettings(2).
		Reset all values in arrisRouterLanTable and arrisRouterWirelessCfg to their defaults by setting this value to resetDefaults(3).
		Restart the Wireless LAN only (4)."
	::= { arrisRouterLanConfig 6 }

-- This is Device Discovery config

arrisRouterLanSrvDiscoveryObjs OBJECT IDENTIFIER ::= { arrisRouterLanConfig 7 }

arrisRouterLanUPnPAdvTime OBJECT-TYPE
     SYNTAX      Unsigned32
     MAX-ACCESS  read-write
     STATUS      current
     DESCRIPTION "Get/set Advertisement Period for UPnP."
     ::= { arrisRouterLanSrvDiscoveryObjs 1 }

arrisRouterLanUPnPTtl OBJECT-TYPE
     SYNTAX      Unsigned32
     MAX-ACCESS  read-write
     STATUS      current
     DESCRIPTION "Get/set Time To Live for UPnP."
     ::= { arrisRouterLanSrvDiscoveryObjs 2 }

arrisRouterLanZeroConf OBJECT-TYPE
     SYNTAX      TruthValue
     MAX-ACCESS  read-write
     STATUS      current
     DESCRIPTION "Get/set whether or not Zero Config is enabled."
     ::= { arrisRouterLanSrvDiscoveryObjs 3 }

arrisRouterLanQosUPnP OBJECT-TYPE
     SYNTAX      TruthValue
     MAX-ACCESS  read-write
     STATUS      current
     DESCRIPTION "Get/set whether or not QoS for UPnP is enabled. "
     ::= { arrisRouterLanSrvDiscoveryObjs 4 }

-- This is Wireless (WI-FI) config

arrisRouterLanEtherPortTable OBJECT-TYPE
      SYNTAX      SEQUENCE OF ArrisRouterLanEtherPortEntry
      MAX-ACCESS  not-accessible
      STATUS      current
      DESCRIPTION "Table contains configuration information for the physical Ethernet ports."
      ::= { arrisRouterLanConfig 8 }

arrisRouterLanEtherPortEntry OBJECT-TYPE
      SYNTAX      ArrisRouterLanEtherPortEntry
      MAX-ACCESS  not-accessible
      STATUS      current
      DESCRIPTION "Table contains configuration information for the physical Ethernet ports."
      INDEX { arrisRouterLanEtherPortIdx }
      ::= { arrisRouterLanEtherPortTable 1 }

ArrisRouterLanEtherPortEntry ::= SEQUENCE {
        arrisRouterLanEtherPortIdx		Unsigned32,
        arrisRouterLanEtherPortIFIndex 		Integer32,
        arrisRouterLanEtherPortEnabled		INTEGER,
        arrisRouterLanEtherPortDuplex		INTEGER,
        arrisRouterLanEtherPortSpeed		Integer32,
        arrisRouterLanEtherPortAuto		INTEGER,
        arrisRouterLanEtherPortHasLink      	TruthValue,
        arrisRouterLanEtherPortEEE              INTEGER
        }

arrisRouterLanEtherPortIdx OBJECT-TYPE
     SYNTAX      Unsigned32
     MAX-ACCESS  not-accessible
     STATUS      current
     DESCRIPTION "Table index."
     ::= { arrisRouterLanEtherPortEntry 1 }

arrisRouterLanEtherPortIFIndex OBJECT-TYPE
     SYNTAX      Integer32
     MAX-ACCESS  read-only
     STATUS      current
     DESCRIPTION "Corresponding IF Index in the MIB-2 IFTable."
     ::= { arrisRouterLanEtherPortEntry 2 }

arrisRouterLanEtherPortEnabled OBJECT-TYPE
     SYNTAX      INTEGER { disabled(0), enabled(1) }
     MAX-ACCESS  read-write
     STATUS      current
     DESCRIPTION "Get and set if this Ethernet port is enabled."
     DEFVAL	{ enabled }
     ::= { arrisRouterLanEtherPortEntry 3 }

arrisRouterLanEtherPortDuplex OBJECT-TYPE
     SYNTAX      INTEGER { halfDuplex(0), fullDuplex(1) }
     MAX-ACCESS  read-write
     STATUS      current
     DESCRIPTION "Get and set the duplex setting for this Ethernet port.
                    The device may need to be rebooted to apply this settings"
     DEFVAL	{ fullDuplex }
     ::= { arrisRouterLanEtherPortEntry 4 }

arrisRouterLanEtherPortSpeed OBJECT-TYPE
     SYNTAX      Integer32
     MAX-ACCESS  read-write
     STATUS      current
     DESCRIPTION "Get and set the speed setting for this Ethernet port.  This is the configured speed of the port if auto-negotiate is OFF.
                    To query the actual current speed of the interface use the MIB-2 OID: .iso.org.dod.internet.mgmt.mib-2.interfaces.ifTable.ifEntry.ifSpeed.
                    Valid values are 10, 100, and 1000 in units of megabits/second.
                    The device may need to be rebooted to apply this settings."
     ::= { arrisRouterLanEtherPortEntry 5 }

arrisRouterLanEtherPortAuto OBJECT-TYPE
     SYNTAX      INTEGER { manualConfigure(0), autoNegotiate(1) }
     MAX-ACCESS  read-write
     STATUS      current
     DESCRIPTION "Get and set the 'auto-negotiate' setting for this Ethernet port.
                 If the port is set to 'autoNegotiate', the settings for 'arrisRouterLanEtherPortDuplex'
                 and 'arrisRouterLanEtherPortSpeed' are not used.
                 The device may need to be rebooted to apply this settings"
     DEFVAL	{ autoNegotiate }
     ::= { arrisRouterLanEtherPortEntry 6 }

arrisRouterLanEtherPortHasLink OBJECT-TYPE
     SYNTAX      TruthValue
     MAX-ACCESS  read-only
     STATUS      current
     DESCRIPTION "Get if the Ethernet port has 'link' or not."
     ::= { arrisRouterLanEtherPortEntry 7 }

arrisRouterLanEtherPortEEE OBJECT-TYPE
     SYNTAX      INTEGER { disabled(0), enabled(1) }
     MAX-ACCESS  read-write
     STATUS      current
     DESCRIPTION "Enable or disable Energy Efficient Ethernet."
     ::= { arrisRouterLanEtherPortEntry 8 }

-- RIPng settings

arrisRouterRIPngObjects		OBJECT IDENTIFIER ::= { arrisRouterLanConfig 9 }

arrisRouterRIPngEnable OBJECT-TYPE
     SYNTAX      TruthValue
     MAX-ACCESS  read-write
     STATUS      current
     DESCRIPTION "IPV6 Enable/disable RIPng ."
     ::= { arrisRouterRIPngObjects 1 }

arrisRouterRIPngAddr OBJECT-TYPE
     SYNTAX      InetAddressIPv6
     MAX-ACCESS  read-write
     STATUS      current
     DESCRIPTION "IPV6 RIPng unicast reporting destination IP address."
     ::= { arrisRouterRIPngObjects 2 }

arrisRouterRIPngSubnetEnable OBJECT-TYPE
     SYNTAX      TruthValue
     MAX-ACCESS  read-write
     STATUS      current
     DESCRIPTION "IPV6 Enable/disable RIPng subnet."
     ::= { arrisRouterRIPngObjects 3 }

arrisRouterRIPngRoutedSubnetAddr OBJECT-TYPE
     SYNTAX      InetAddressIPv6
     MAX-ACCESS  read-write
     STATUS      current
     DESCRIPTION "IPV6 specific network in the configured subnet that will be adverstised and routed."
     ::= { arrisRouterRIPngObjects 4 }

arrisRouterRIPngRoutedSubnetPrefixLength OBJECT-TYPE
     SYNTAX      Integer32
     MAX-ACCESS  read-write
     STATUS      current
     DESCRIPTION "IPV6 rip prefix length."
     DEFVAL	     { 64 }
     ::= { arrisRouterRIPngObjects 5 }

arrisRouterRIPngSendCMInterface OBJECT-TYPE
     SYNTAX      TruthValue
     MAX-ACCESS  read-write
     STATUS      current
     DESCRIPTION "IPV6 If set to TRUE, then RIPng advertisements will be sent via the CM IP interface.
                  If this set to FALSE, then RIP advertisements will be sent via the eRouter WAN IP interface."
     DEFVAL	     { false }
     ::= { arrisRouterRIPngObjects 6 }


arrisRouterARPObjects		OBJECT IDENTIFIER ::= { arrisRouterLanConfig 10 }


arrisRouterARPTableString OBJECT-TYPE
     SYNTAX      DisplayString
     MAX-ACCESS  read-only
     STATUS      current
     DESCRIPTION "Returns the current ARP table in format MAC=IP delimited by a semicolon, i.e 00:1D:CD:FA:16:F1=192.168.0.10;00:1D:CD:FA:16:F2=192.168.0.11"
     ::= { arrisRouterARPObjects 1 }

arrisRouterARPTableClear OBJECT-TYPE
     SYNTAX      INTEGER { clear(1) }
     MAX-ACCESS  read-write
     STATUS      current
     DESCRIPTION "Set to clear(1) to clear the ARP table."
     ::= { arrisRouterARPObjects 2 }

arrisRouterARPTableAdd OBJECT-TYPE
     SYNTAX      DisplayString
     MAX-ACCESS  read-write
     STATUS      current
     DESCRIPTION "Set a string in the format: MAC=IP to add a new entry to the ARP table.  This entry will be added permanently with no timeout value."
     ::= { arrisRouterARPObjects 3 }

arrisRouterARPAutoInjectDisable OBJECT-TYPE
     SYNTAX      TruthValue
     MAX-ACCESS  read-write
     STATUS      deprecated
     DESCRIPTION "Set to true to disable ARP table auto-population."
     DEFVAL { false }
     ::= { arrisRouterARPObjects 4 }

-- DHCP Options setting

arrisRouterLanSrvDHCPOptionsTable OBJECT-TYPE
      SYNTAX      SEQUENCE OF ArrisRouterLanSrvDHCPOptionsEntry
      MAX-ACCESS  not-accessible
      STATUS      current
      DESCRIPTION "Table contains DHCP server option information for a specific Lan."
      ::= { arrisRouterLanConfig 11 }

arrisRouterLanSrvDHCPOptionsEntry OBJECT-TYPE
      SYNTAX      ArrisRouterLanSrvDHCPOptionsEntry
      MAX-ACCESS  not-accessible
      STATUS      current
      DESCRIPTION "Table contains DHCP server option information for a specific Lan."
      INDEX { ifIndex, arrisRouterLanSrvDHCPOptionsIdx }	--from IF-MIB
      ::= { arrisRouterLanSrvDHCPOptionsTable 1 }

ArrisRouterLanSrvDHCPOptionsEntry ::= SEQUENCE {
            arrisRouterLanSrvDHCPOptionsIdx                        Unsigned32,
            arrisRouterLanSrvDHCPOptionsEnable                     TruthValue,
            arrisRouterLanSrvDHCPOptionsIPAddrType                 InetAddressType,
            arrisRouterLanSrvDHCPOptionsTag                        Unsigned32,
            arrisRouterLanSrvDHCPOptionsValue                      DisplayString,
            arrisRouterLanSrvDHCPOptionsRowStatus                  RowStatus
            }

arrisRouterLanSrvDHCPOptionsIdx OBJECT-TYPE
     SYNTAX      Unsigned32
     MAX-ACCESS  not-accessible
     STATUS      current
     DESCRIPTION "Table index.
                  NOTE: For TS7.x, this mib only supports (1..4)."
     ::= { arrisRouterLanSrvDHCPOptionsEntry 1 }

arrisRouterLanSrvDHCPOptionsEnable OBJECT-TYPE
     SYNTAX      TruthValue
     MAX-ACCESS  read-only
     STATUS      current
     DESCRIPTION "DHCP Option Enable"
     DEFVAL	     { true }
     ::= { arrisRouterLanSrvDHCPOptionsEntry 2 }

arrisRouterLanSrvDHCPOptionsIPAddrType OBJECT-TYPE
     SYNTAX      InetAddressType
     MAX-ACCESS  read-only
     STATUS      current
     DESCRIPTION "Internet address type for the DHCP server"
     ::= { arrisRouterLanSrvDHCPOptionsEntry 3 }

arrisRouterLanSrvDHCPOptionsTag OBJECT-TYPE
     SYNTAX      Unsigned32 (1..254)
     MAX-ACCESS  read-only
     STATUS      current
     DESCRIPTION "DHCP Option Number"
     ::= { arrisRouterLanSrvDHCPOptionsEntry 4 }

arrisRouterLanSrvDHCPOptionsValue OBJECT-TYPE
     SYNTAX DisplayString (SIZE(0..64))
     MAX-ACCESS read-only
     STATUS current
     DESCRIPTION "DHCP Option Value."
     ::= { arrisRouterLanSrvDHCPOptionsEntry 5 }

arrisRouterLanSrvDHCPOptionsRowStatus OBJECT-TYPE
     SYNTAX      RowStatus
     MAX-ACCESS  read-create
     STATUS      current
     DESCRIPTION "RowStatus used to add or remove DHCP Options row entries"
     ::= { arrisRouterLanSrvDHCPOptionsEntry 6 }

arrisRouterLanArrisDeviceLeaseTime OBJECT-TYPE
     SYNTAX      Unsigned32 (30..4294967295)
     UNITS       "seconds"
     MAX-ACCESS  read-write
     STATUS      current
     DESCRIPTION "The length of the lease time for dynamic (DHCP) IP addresses handed out by this device. It must be greater than 30."
     DEFVAL { 86400 }
     ::= { arrisRouterLanConfig 12 }

arrisRouterLanMaxIPv6RAInterval OBJECT-TYPE
     SYNTAX      Unsigned32
     UNITS       "seconds"
     MAX-ACCESS  read-write
     STATUS      current
     DESCRIPTION "The maximum interval between IPv6 router advertisements. Must
                 be positive and no less than minimum IPv6 RA interval."
     DEFVAL	     { 3 }
     ::= { arrisRouterLanConfig 13 }

arrisRouterLanMinIPv6RAInterval OBJECT-TYPE
     SYNTAX      Unsigned32
     UNITS       "seconds"
     MAX-ACCESS  read-write
     STATUS      current
     DESCRIPTION "The minimum interval between IPv6 router advertisements. Must
                  be positive and no more than maximum IPv6 RA interval."
     DEFVAL	 { 3 }
     ::= { arrisRouterLanConfig 14 }

arrisRouterLanBridgeType OBJECT-TYPE
     SYNTAX      INTEGER { subnetBridge(0), fullBridge(1)}
     MAX-ACCESS  read-write
     STATUS      current
     DESCRIPTION "Control the behavior of switching NAT Mode among 'RoutedWithNAT', 'RoutedWithoutNAT' and 'Bridged' on LAN Setup WEB GUI page.
                  subnetBridge(0): When switch NAT mode from 'RoutedWithNAT' or 'RoutedWithoutNAT' to 'Bridged', put the subnet into subnet level bridge mode.
                                   When switch NAT mode from 'Bridged' back to 'RoutedWithoutNAT' or 'RoutedWithNAT', put the subnet into route mode.

                  fullBridge(1):   When switch NAT mode from 'RoutedWithNAT' or 'RoutedWithoutNAT' to 'Bridged', put the whole eRouter into device level bridge mode.
                                   No IP address will be assigned to eRouter WAN interface.
                                   When switch NAT mode from 'Bridged' back to 'RoutedWithoutNAT' or 'RoutedWithNAT', put eRouter into default dualStack mode."
     DEFVAL { subnetBridge }
     ::= { arrisRouterLanConfig 15 }

-- This is USB port information

arrisRouterLanUSBPortTable OBJECT-TYPE
      SYNTAX      SEQUENCE OF ArrisRouterLanUSBPortEntry
      MAX-ACCESS  not-accessible
      STATUS      current
      DESCRIPTION "Table contains configuration information for the physical USB ports."
      ::= { arrisRouterLanConfig 16 }

arrisRouterLanUSBPortEntry OBJECT-TYPE
      SYNTAX      ArrisRouterLanUSBPortEntry
      MAX-ACCESS  not-accessible
      STATUS      current
      DESCRIPTION "Table contains configuration information for the physical USB ports."
      INDEX { arrisRouterLanUSBPortIdx }
      ::= { arrisRouterLanUSBPortTable 1 }

ArrisRouterLanUSBPortEntry ::= SEQUENCE {
		arrisRouterLanUSBPortIdx			Unsigned32,
		arrisRouterLanUSBPortHasLink		TruthValue,
		arrisRouterLanUSBPortDescr		       DisplayString,
		arrisRouterLanUSBPortSerialNum	       DisplayString,
		arrisRouterLanUSBPortSpeed              Integer32,
		arrisRouterLanUSBPortManuf               DisplayString,
		arrisRouterLanUSBPortStorageNam      DisplayString,
		arrisRouterLanUSBPortFileSys              DisplayString,
		arrisRouterLanUSBPortSpaceAvail        DisplayString,
		arrisRouterLanUSBPortTotalSpace        DisplayString,
		arrisRouterLanUsbPortFoldersFile       DisplayString,
		arrisRouterLanUSBPortDelStorage        TruthValue
		}

arrisRouterLanUSBPortIdx OBJECT-TYPE
     SYNTAX      Unsigned32 (1..2)
     MAX-ACCESS  not-accessible
     STATUS      current
     DESCRIPTION "Table index"
     ::= { arrisRouterLanUSBPortEntry 1 }

arrisRouterLanUSBPortHasLink OBJECT-TYPE
     SYNTAX      TruthValue
     MAX-ACCESS  read-only
     STATUS      current
     DESCRIPTION "Get whether the USB port has 'link' or not."
     ::= { arrisRouterLanUSBPortEntry 2 }

arrisRouterLanUSBPortDescr OBJECT-TYPE
    SYNTAX      DisplayString (SIZE (0..64))
    MAX-ACCESS  read-only
    STATUS      current
    DESCRIPTION "Description of the connected USB device."
    ::= { arrisRouterLanUSBPortEntry 3 }

arrisRouterLanUSBPortSerialNum OBJECT-TYPE
    SYNTAX      DisplayString (SIZE (0..64))
    MAX-ACCESS  read-only
    STATUS      current
    DESCRIPTION "Serial number of the connected USB device."
    ::= { arrisRouterLanUSBPortEntry 4 }

arrisRouterLanUSBPortSpeed OBJECT-TYPE
     SYNTAX      Integer32
     UNITS	   "Mbps"
     MAX-ACCESS  read-only
     STATUS      current
     DESCRIPTION "Get the speed for the USB port."
     ::= { arrisRouterLanUSBPortEntry 5 }

arrisRouterLanUSBPortManuf OBJECT-TYPE
    SYNTAX      DisplayString (SIZE (0..64))
    MAX-ACCESS  read-only
    STATUS      current
    DESCRIPTION "Get manufacturer information of the connected USB device."
    ::= { arrisRouterLanUSBPortEntry 6 }

arrisRouterLanUSBPortStorageNam OBJECT-TYPE
    SYNTAX      DisplayString (SIZE (0..32))
    MAX-ACCESS  read-write
    STATUS      current
    DESCRIPTION "Get/Set storage name of the connected USB device."
    ::= { arrisRouterLanUSBPortEntry 7 }

arrisRouterLanUSBPortFileSys OBJECT-TYPE
    SYNTAX      DisplayString (SIZE (0..32))
    MAX-ACCESS  read-only
    STATUS      current
    DESCRIPTION "Get file system used by the connected USB device."
    ::= { arrisRouterLanUSBPortEntry 8 }

arrisRouterLanUSBPortSpaceAvail OBJECT-TYPE
    SYNTAX      DisplayString (SIZE (0..32))
    MAX-ACCESS  read-only
    STATUS      current
    DESCRIPTION "Space available of the connected USB device."
    ::= { arrisRouterLanUSBPortEntry 9 }

arrisRouterLanUSBPortTotalSpace OBJECT-TYPE
    SYNTAX      DisplayString (SIZE (0..32))
    MAX-ACCESS  read-only
    STATUS      current
    DESCRIPTION "Total space of the connected USB device."
    ::= { arrisRouterLanUSBPortEntry 10 }

arrisRouterLanUsbPortFoldersFile OBJECT-TYPE
     SYNTAX      DisplayString (SIZE (0..128))
     MAX-ACCESS  read-only
     STATUS      current
     DESCRIPTION "save file name, the file is used to save first-level folders on USB"
     ::= { arrisRouterLanUSBPortEntry 11 }

arrisRouterLanUSBPortDelStorage OBJECT-TYPE
    SYNTAX     TruthValue
    MAX-ACCESS read-write
    STATUS     current
    DESCRIPTION "Set to true to delete the USB storage."
    ::= { arrisRouterLanUSBPortEntry 12 }

-- This is file sharing information
arrisRouterLanFileSharingObjs		OBJECT IDENTIFIER ::= { arrisRouterLanConfig 17 }

arrisRouterLanFilesharingEnable OBJECT-TYPE
     SYNTAX      TruthValue
     MAX-ACCESS  read-write
     STATUS      current
     DESCRIPTION "enable/disable fire sharing"
     DEFVAL	{ true }
     ::= { arrisRouterLanFileSharingObjs 1 }

arrisRouterLanFilesharingDevName OBJECT-TYPE
     SYNTAX      DisplayString (SIZE (0..32))
     MAX-ACCESS  read-write
     STATUS      current
     DESCRIPTION "network device name"
     ::= { arrisRouterLanFileSharingObjs 2 }

arrisRouterLanFileSharingTable OBJECT-TYPE
      SYNTAX      SEQUENCE OF ArrisRouterLanFilesharingEntry
      MAX-ACCESS  not-accessible
      STATUS      current
      DESCRIPTION "Table contains the information of the sharing."
      ::= { arrisRouterLanFileSharingObjs 3 }

arrisRouterLanFileSharingEntry OBJECT-TYPE
      SYNTAX      ArrisRouterLanFilesharingEntry
      MAX-ACCESS  not-accessible
      STATUS      current
      DESCRIPTION "Table contains information of the sharing."
      INDEX { arrisRouterLanFilesharingIdx }
      ::= { arrisRouterLanFileSharingTable 1 }

ArrisRouterLanFilesharingEntry ::= SEQUENCE {
		arrisRouterLanFilesharingIdx            Unsigned32,
		arrisRouterLanFilesharingRowStatus      RowStatus,
		arrisRouterLanFilesharingUsbPort        Unsigned32,
		arrisRouterLanFilesharingDirectory      DisplayString,
		arrisRouterLanFilesharingName           DisplayString,
		arrisRouterLanFilesharingEnableHttp     TruthValue,
		arrisRouterLanFilesharingEnableFtp      TruthValue,
		arrisRouterLanFilesharingVisibility     TruthValue,
		arrisRouterLanFilesharingEveryOnePerm   INTEGER,
		arrisRouterLanFilesharingDesc           DisplayString
		}


arrisRouterLanFilesharingIdx OBJECT-TYPE
     SYNTAX      Unsigned32 (1..32)
     MAX-ACCESS  not-accessible
     STATUS      current
     DESCRIPTION "Table index"
     ::= { arrisRouterLanFileSharingEntry 1 }

arrisRouterLanFilesharingRowStatus OBJECT-TYPE
     SYNTAX      RowStatus
     MAX-ACCESS  read-create
     STATUS      current
     DESCRIPTION "RowStatus used to add/remove rows from the table"
     ::= { arrisRouterLanFileSharingEntry 2 }

arrisRouterLanFilesharingUsbPort OBJECT-TYPE
     SYNTAX      Unsigned32 (1..2)
     MAX-ACCESS  read-create
     STATUS      current
     DESCRIPTION "USB port"
     ::= { arrisRouterLanFileSharingEntry 3 }

arrisRouterLanFilesharingDirectory OBJECT-TYPE
     SYNTAX      DisplayString (SIZE (0..128))
     MAX-ACCESS  read-create
     STATUS      current
     DESCRIPTION "share directory"
     ::= { arrisRouterLanFileSharingEntry 4 }

arrisRouterLanFilesharingName OBJECT-TYPE
     SYNTAX      DisplayString (SIZE (0..32))
     MAX-ACCESS  read-create
     STATUS      current
     DESCRIPTION "share name"
     ::= { arrisRouterLanFileSharingEntry 5 }

arrisRouterLanFilesharingEnableHttp OBJECT-TYPE
     SYNTAX      TruthValue
     MAX-ACCESS  read-create
     STATUS      current
     DESCRIPTION "enable/disable http for this share"
     DEFVAL	{ false }
     ::= { arrisRouterLanFileSharingEntry 6 }

arrisRouterLanFilesharingEnableFtp OBJECT-TYPE
     SYNTAX      TruthValue
     MAX-ACCESS  read-create
     STATUS      current
     DESCRIPTION "enable/disable ftp for this share"
     DEFVAL	{ false }
     ::= { arrisRouterLanFileSharingEntry 7 }

arrisRouterLanFilesharingVisibility OBJECT-TYPE
     SYNTAX      TruthValue
     MAX-ACCESS  read-create
     STATUS      current
     DESCRIPTION "whether permit everyone to access the share"
     DEFVAL	{ true }
     ::= { arrisRouterLanFileSharingEntry 8}

arrisRouterLanFilesharingEveryOnePerm OBJECT-TYPE
     SYNTAX      INTEGER { noAccess(0), readOnly(1), writeOnly(2), readandWrite(3)}
     MAX-ACCESS  read-create
     STATUS      current
     DESCRIPTION "everyone permission, it is available only when arrisRouterLanFilesharingVisibility is set to TRUE"
     ::= { arrisRouterLanFileSharingEntry 9}

arrisRouterLanFilesharingDesc OBJECT-TYPE
     SYNTAX      DisplayString (SIZE (0..128))
     MAX-ACCESS  read-create
     STATUS      current
     DESCRIPTION "description for the share"
     ::= { arrisRouterLanFileSharingEntry 10 }

arrisRouterLanLocalUserTable OBJECT-TYPE
      SYNTAX      SEQUENCE OF ArrisRouterLanLocalUserEntry
      MAX-ACCESS  not-accessible
      STATUS      current
      DESCRIPTION "Table contains the user permissions for share ."
      ::= { arrisRouterLanFileSharingObjs 4 }

arrisRouterLanLocalUserEntry OBJECT-TYPE
      SYNTAX      ArrisRouterLanLocalUserEntry
      MAX-ACCESS  not-accessible
      STATUS      current
      DESCRIPTION "Table contains the user permissions for share."
      INDEX { arrisRouterLanLocalUserIdx }
      ::= { arrisRouterLanLocalUserTable 1 }

ArrisRouterLanLocalUserEntry ::= SEQUENCE {
		arrisRouterLanLocalUserIdx        Unsigned32,
		arrisRouterLanLocalUserRowStatus  RowStatus,
		arrisRouterLanLocalUserName       DisplayString,
		arrisRouterLanLocalUserPasswd     DisplayString
		}

arrisRouterLanLocalUserIdx OBJECT-TYPE
     SYNTAX      Unsigned32 (1..32)
     MAX-ACCESS  not-accessible
     STATUS      current
     DESCRIPTION "Table index"
     ::= { arrisRouterLanLocalUserEntry 1 }

 arrisRouterLanLocalUserRowStatus OBJECT-TYPE
     SYNTAX      RowStatus
     MAX-ACCESS  read-create
     STATUS      current
     DESCRIPTION "RowStatus used to add/remove rows from the table"
     ::= { arrisRouterLanLocalUserEntry 2 }

arrisRouterLanLocalUserName OBJECT-TYPE
     SYNTAX      DisplayString (SIZE (0..32))
     MAX-ACCESS  read-create
     STATUS      current
     DESCRIPTION "Local user name"
     ::= { arrisRouterLanLocalUserEntry 3 }

arrisRouterLanLocalUserPasswd OBJECT-TYPE
     SYNTAX      DisplayString (SIZE (0..32))
     MAX-ACCESS  read-create
     STATUS      current
     DESCRIPTION "Local user password"
     ::= { arrisRouterLanLocalUserEntry 4 }

arrisRouterLanFilesharingPermitTable OBJECT-TYPE
      SYNTAX      SEQUENCE OF ArrisRouterLanFilesharingPermitEntry
      MAX-ACCESS  not-accessible
      STATUS      current
      DESCRIPTION "Table contains the user permissions for share ."
      ::= { arrisRouterLanFileSharingObjs 5 }

arrisRouterLanFilesharingPermitEntry OBJECT-TYPE
      SYNTAX      ArrisRouterLanFilesharingPermitEntry
      MAX-ACCESS  not-accessible
      STATUS      current
      DESCRIPTION "Table contains the user permissions for share."
      INDEX { arrisRouterLanFilesharingIdx,arrisRouterLanLocalUserIdx }
      ::= { arrisRouterLanFilesharingPermitTable 1 }

ArrisRouterLanFilesharingPermitEntry ::= SEQUENCE {
		arrisRouterLanFilesharingPermitvalue     INTEGER
		}

arrisRouterLanFilesharingPermitvalue OBJECT-TYPE
     SYNTAX      INTEGER { noAccess(0), readOnly(1), writeOnly(2), readandWrite(3)}
     MAX-ACCESS  read-create
     STATUS      current
     DESCRIPTION "User permission, it is available only when arrisRouterLanFilesharingVisibility is set to FALSE"
     ::= { arrisRouterLanFilesharingPermitEntry 1}

-- This is LAN QoS config

arrisRouterLanQoSObjs OBJECT IDENTIFIER ::= { arrisRouterLanConfig 18 }

arrisRouterLanQoSObjsEnable OBJECT-TYPE
     SYNTAX      TruthValue
     MAX-ACCESS  read-write
     STATUS      current
     DESCRIPTION "Enable/Disable LAN QoS."
     ::= { arrisRouterLanQoSObjs 1 }

arrisRouterLanIPv6RALifetime OBJECT-TYPE
         SYNTAX      Unsigned32
         UNITS       "seconds"
         MAX-ACCESS  read-write
         STATUS      current
         DESCRIPTION "The value to be placed in the router lifetime field of
                      router advertisements sent from this interface.  This value
                      MUST be either 0 or between ipv6RouterAdvertMaxInterval and 9000 seconds.

                      A value of zero indicates that the router is not to be used as a default router.
                      The default is 1800"
         DEFVAL      { 1800 }
         ::= { arrisRouterLanConfig 19 }

arrisRouterLanMaxNatSessions OBJECT-TYPE
     SYNTAX      Unsigned32
     MAX-ACCESS  read-write
     STATUS      current
     DESCRIPTION "MIB to set the maximum NAT sessions"
     DEFVAL	{ 16384 }
     ::= { arrisRouterLanConfig 20 }

-- Static Routing table

arrisRouterStaticRoutingTable  OBJECT-TYPE
    SYNTAX      SEQUENCE OF ArrisRouterStaticRoutingEntry
    MAX-ACCESS  not-accessible
    STATUS      current
    DESCRIPTION "A table of static routing."
    ::= { arrisRouterLanConfig 21 }

arrisRouterStaticRoutingEntry OBJECT-TYPE
    SYNTAX      ArrisRouterStaticRoutingEntry
    MAX-ACCESS  not-accessible
    STATUS      current
    DESCRIPTION "A table of static routing"
    INDEX       { arrisRouterStaticRoutingIndex }
    ::= { arrisRouterStaticRoutingTable 1 }

ArrisRouterStaticRoutingEntry ::=
    SEQUENCE    {
                arrisRouterStaticRoutingIndex			Unsigned32,
                arrisRouterStaticRoutingDesc			DisplayString,
                arrisRouterStaticRoutingDestinationNet		InetAddress,
                arrisRouterStaticRoutingSubnetMask		InetAddress,
                arrisRouterStaticRoutingGatewayAddr		InetAddress,
                arrisRouterStaticRoutingRowStatus		RowStatus
    }

arrisRouterStaticRoutingIndex OBJECT-TYPE
    SYNTAX      Unsigned32
    MAX-ACCESS  not-accessible
    STATUS      current
    DESCRIPTION "Indicates the instance of this table row."
    ::= { arrisRouterStaticRoutingEntry 1 }

arrisRouterStaticRoutingDesc OBJECT-TYPE
    SYNTAX      DisplayString (SIZE (0..32))
    MAX-ACCESS  read-create
    STATUS      current
    DESCRIPTION "A textual description or name for this static routing rule."
    ::= { arrisRouterStaticRoutingEntry 2 }

arrisRouterStaticRoutingDestinationNet OBJECT-TYPE
    SYNTAX      InetAddress
    MAX-ACCESS  read-create
    STATUS      current
    DESCRIPTION "Destination net to be routed to."
    ::= { arrisRouterStaticRoutingEntry 3 }

arrisRouterStaticRoutingSubnetMask OBJECT-TYPE
    SYNTAX      InetAddress
    MAX-ACCESS  read-create
    STATUS      current
    DESCRIPTION "Subnet mask for destination net."
    ::= { arrisRouterStaticRoutingEntry 4 }

arrisRouterStaticRoutingGatewayAddr OBJECT-TYPE
    SYNTAX      InetAddress
    MAX-ACCESS  read-create
    STATUS      current
    DESCRIPTION "Gateway address for destination net."
    ::= { arrisRouterStaticRoutingEntry 5 }

arrisRouterStaticRoutingRowStatus OBJECT-TYPE
    SYNTAX      RowStatus
    MAX-ACCESS  read-create
    STATUS      current
    DESCRIPTION "Row status to add/remove rows"
    ::= { arrisRouterStaticRoutingEntry 6 }

arrisRouterLanEthernetGreenModeEnable OBJECT-TYPE
    SYNTAX      TruthValue
    MAX-ACCESS  read-write
    STATUS      current
    DESCRIPTION "Enable or Disable Green mode for Ethernet."
    DEFVAL { false }
    ::= { arrisRouterLanConfig 22 }

arrisRouterLanEthernetGreenModeStatus OBJECT-TYPE
    SYNTAX      INTEGER {
           none(0),
           active(1),
           inactive(2)
           }
    MAX-ACCESS  read-only
    STATUS      current
    DESCRIPTION  "Current status of Ethernet Green Mode."
    ::= { arrisRouterLanConfig 23}

arrisRouterLanIgmpProxyLLQI OBJECT-TYPE
    SYNTAX      INTEGER (1..32)
    UNITS       "seconds"
    MAX-ACCESS  read-write
    STATUS      current
    DESCRIPTION "Last Listener Query Interval of multicast address specific queries"
    ::= { arrisRouterLanConfig 24 }

-- This is Wireless (WI-FI) config

arrisRouterWiFiCountry OBJECT-TYPE
     SYNTAX      DisplayString (SIZE(2))
     MAX-ACCESS  read-write
     STATUS      current
     DESCRIPTION "Country where wireless is located.
                  Available countries are 'US', 'EU' and 'JP'.
		  If the country is set to US(United States), channels 1-11 can be used for 'arrisRouterWiFiChannel'.
		  If the country is set to EU(Europe), channels 1-13 can be used for 'arrisRouterWiFiChannel'.
		  If the country is set to JP(Japan), channel 14 can be used for 'arrisRouterWiFiChannel'."
     ::= { arrisRouterWirelessCfg 1 }

arrisRouterWiFiChannel OBJECT-TYPE
     SYNTAX     Unsigned32 (0..216)
     MAX-ACCESS  read-write
     STATUS      current
     DESCRIPTION  "Controls and reflects the current channel number (802.11g) or
                 control channel (802.11n).

                 If set to (0), the device will be put in auto-channel mode where it automatically scans
                 for the least-crowded channel.

                 For 802.11g cards, available channels are 1-14.
                 For 802.11n cards, available channels are 34-216.
                 Channel selection is also subject to restrictions based on the selected
                 country code."
     ::= { arrisRouterWirelessCfg 2 }

arrisRouterWiFiMode OBJECT-TYPE
     SYNTAX      INTEGER { unknown(-1), mixBG(0), bOnly(1), gOnly(4), nOnly(6), mixGN(7), mixBGN(9) }
     MAX-ACCESS  read-write
     STATUS      current
     DESCRIPTION "Controls and reflects the behavior of the device with regards to which
                flavor of 802.11 is used."
     ::= { arrisRouterWirelessCfg 3 }

arrisRouterWiFiBGProtect OBJECT-TYPE
     SYNTAX      TruthValue
     MAX-ACCESS  read-write
     STATUS      current
     DESCRIPTION "Controls and reflects the state of 54g protection.  If set to true(1),
                 the AP will use RTS/CTS to improve 802.11g performance in mixed
                 802.11g/802.11b networks.  Set to false(2) to maximize 802.11g
                 throughput under most conditions.
		 NOTE: The default value for this mib is false when Time Warner uses TS9.x loads."
     DEFVAL { true }
     ::= { arrisRouterWirelessCfg 4 }

arrisRouterWiFiBeaconInterval OBJECT-TYPE
     SYNTAX      Unsigned32 (1..65535)
     UNITS		 "milliseconds"
     MAX-ACCESS  read-write
     STATUS      current
     DESCRIPTION "Amount of time between beacon transmissions."
     DEFVAL { 100 }
     ::= { arrisRouterWirelessCfg 5 }

arrisRouterWiFiDTIMInterval OBJECT-TYPE
     SYNTAX      Unsigned32 (1..255)
     UNITS		 "milliseconds"
     MAX-ACCESS  read-write
     STATUS      current
     DESCRIPTION "Amount of time between Delivery Traffic Indication Messages."
     DEFVAL { 1 }
     ::= { arrisRouterWirelessCfg 6 }

arrisRouterWiFiTxPreamble OBJECT-TYPE
     SYNTAX      INTEGER { unknown(-1), long(0), short(1) }
     MAX-ACCESS  read-write
     STATUS      current
     DESCRIPTION "This attribute, indicates whether the transfer preamble is long or short."
     DEFVAL { 0 }
     ::= { arrisRouterWirelessCfg 7 }

arrisRouterWiFiRTSThreshold OBJECT-TYPE
     SYNTAX      Unsigned32 (0..2347)
     UNITS       "bytes"
     MAX-ACCESS  read-write
     STATUS      current
     DESCRIPTION
        "The RTS (Request to Send) Threshold indicates the number of bytes in an MPDU,
        below which an RTS/CTS handshake shall not be performed. An RTS/CTS handshake shall
        be performed at the beginning of any frame exchange sequence where the MPDU is of type Data or
        Management, the MPDU has an individual address in the Address1 field, and the length of the MPDU is greater than
        this threshold. Setting this attribute to be larger than the maximum MSDU size shall have the effect of
        turning off the RTS/CTS handshake for frames of Data or Management type transmitted by
        this device. Setting this attribute to zero shall have the effect of turning on the RTS/CTS handshake for
        all frames of Data or Management type transmitted by this device."
     DEFVAL { 2347 }
     ::= { arrisRouterWirelessCfg 8 }

arrisRouterWiFiFragmentThresh OBJECT-TYPE
     SYNTAX      Unsigned32 (256..2346)
     UNITS       "bytes"
     MAX-ACCESS  read-write
     STATUS      current
     DESCRIPTION "This value specifies the maximum size of a packet before the data is fragmented into two or more packets."
     DEFVAL { 2346 }
     ::= { arrisRouterWirelessCfg 9 }

arrisRouterWiFiShortSlot OBJECT-TYPE
     SYNTAX      TruthValue
     MAX-ACCESS  read-write
     STATUS      current
     DESCRIPTION "This returns whether or not the use of short slot timing mode is on or off (long).
                  The amount of time a device waits after a collision before retransmitting a packet.
                  You can increase throughput on 802.11g, 2.4-GHz radios by enabling short slot time.
                  Use the new arrisRouterWiFiShortSlotEnhanced to set to 'auto' mode."
     DEFVAL { true }
     ::= { arrisRouterWirelessCfg 10 }

arrisRouterWiFiFrameBurst OBJECT-TYPE
     SYNTAX      TruthValue
     MAX-ACCESS  read-write
     STATUS      current
     DESCRIPTION "Bursting may increase the throughput of link connection in certain
                    conditions. This can result in the ability to support higher data
                    throughput in mixed and uniform networks. Also known as 'XPress Technology'"
     DEFVAL { true }
     ::= { arrisRouterWirelessCfg 11 }

arrisRouterWiFiEnableRadio OBJECT-TYPE
     SYNTAX      TruthValue
     MAX-ACCESS  read-write
     STATUS      current
     DESCRIPTION "Enable or disable WiFi radio."
     DEFVAL { true }
     ::= { arrisRouterWirelessCfg 12 }

arrisRouterWiFiTxPower OBJECT-TYPE
     SYNTAX		Integer32 (1..8)
     MAX-ACCESS  read-write
     STATUS      current
     DESCRIPTION "The TxPowerLevel N currently being used to transmit data.
                Some PHYs also use this value to determine the receiver
                sensitivity requirements for CCA. Note that 0 indicates the value can't be read."
     ::= { arrisRouterWirelessCfg 13 }

arrisRouterWiFiShortRetryLimit OBJECT-TYPE
     SYNTAX      Integer32 (1..255)
     MAX-ACCESS  read-write
     STATUS      current
     DESCRIPTION "Get or set the retry limit of frames longer than the RTS threshold."
     ::= { arrisRouterWirelessCfg 14 }

arrisRouterWiFiLongRetryLimit OBJECT-TYPE
     SYNTAX      Integer32 (1..255)
     MAX-ACCESS  read-write
     STATUS      current
     DESCRIPTION "Get or set the retry limit of frames shorter than the RTS threshold."
     ::= { arrisRouterWirelessCfg 15 }

arrisRouterWiFiOutputPower OBJECT-TYPE
    SYNTAX      INTEGER {
                percent12(12),
                percent25(25),
                percent50(50),
                percent75(75),
                percent100(100)
    }
    MAX-ACCESS  read-write
    STATUS      current
    DESCRIPTION
        "Sets the output power relative to the hardware's maximum capability.
         Now only percent25(25), percent50(50) and percent100(100) can be set,
         they are mapped to Low, medium and high power level which used on GUI."
    DEFVAL { percent100 }
    ::= { arrisRouterWirelessCfg 16 }

arrisRouterWiFiMulticastA OBJECT-TYPE
     SYNTAX		 INTEGER {	auto(0),
                            rate12mbps(12),
                            rate18mbps(18),
                            rate24mbps(24),
                            rate36mbps(36),
                            rate48mbps(48),
                            rate72mbps(72),
                            rate96mbps(96),
                            rate108mbps(108)
                            }
     MAX-ACCESS  read-write
     STATUS      current
     DESCRIPTION "Get or set the multicast rate for 802.11a."
     ::= { arrisRouterWirelessCfg 17 }

arrisRouterWiFiMulticastBG OBJECT-TYPE
     SYNTAX		 INTEGER {	auto(0),
                            bgMrate2mbps(2),
                            bgMrate4mbps(4),
                            bgMrate11mbps(11),
                            bgMrate12mbps(12),
                            bgMrate18mbps(18),
                            bgMrate22mbps(22),
                            bgMrate24mbps(24),
                            bgMrate36mbps(36),
                            bgMrate48mbps(48),
                            bgMrate72mbps(72),
                            bgMrate96mbps(96),
                            bgMrate108mbps(108)
                        }
     MAX-ACCESS  read-write
     STATUS      current
     DESCRIPTION "Get or set the multicast rate for 802.11b/g."
     ::= { arrisRouterWirelessCfg 18 }

arrisRouterWiFiBasicRateSet OBJECT-TYPE
    SYNTAX      INTEGER {
        default(1),
        all(2)
    }
    MAX-ACCESS  read-write
    STATUS      current
    DESCRIPTION
            "Determines which rates are advertised as BASIC rates in the beacon.
             If set to default, the driver defaults for the selected 54gMode will
             be used.  If set to all, all available rates will be advertised as
             BASIC rates regardless of the 54gMode setting."
    DEFVAL { default }
    ::= { arrisRouterWirelessCfg 19 }

arrisRouterWiFiTxRate OBJECT-TYPE
    SYNTAX      INTEGER {
                        auto(0),
                        mbits1(1),
                        mbits2(2),
                        mbits5half(5),
                        mbits6(6),
                        mbits9(9),
                        mbits11(11),
                        mbits12(12),
                        mbits18(18),
                        mbits24(24),
                        mbits36(36),
                        mbits48(48),
                        mbits54(54)
                    }
    MAX-ACCESS  read-write
    STATUS      current
    DESCRIPTION "Forces the transmission rate for the AP to a particular speed."
    DEFVAL { auto }
    ::= { arrisRouterWirelessCfg 20 }


arrisRouterWiFi80211NSettings OBJECT IDENTIFIER ::= { arrisRouterWirelessCfg 21 }

arrisRouterWiFi80211NBand OBJECT-TYPE
    SYNTAX      INTEGER {
        band24G(1),
        band5G(2)
    }
    MAX-ACCESS  read-write
    STATUS      current
    DESCRIPTION
        "Determines which Band that we will be operating in. Either the 2.4G or the 5G Hz.  This only applies to 802.11n mode."
    ::= { arrisRouterWiFi80211NSettings 1 }

arrisRouterWiFiHTMCS OBJECT-TYPE
     SYNTAX  INTEGER { auto(0),
                      legacy(1),
                      mcs0(2),
                      mcs1(3),
                      mcs2(4),
                      mcs3(5),
                      mcs4(6),
                      mcs5(7),
                      mcs6(8),
                      mcs7(9),
                      mcs8(10),
                      mcs9(11),
                      mcs10(12),
                      mcs11(13),
                      mcs12(14),
                      mcs13(15),
                      mcs14(16),
                      mcs15(17),
                      mcs16(18),
                      mcs17(19),
                      mcs18(20),
                      mcs19(21),
                      mcs20(22),
                      mcs21(23),
                      mcs22(24),
                      mcs23(25)
                    }
     MAX-ACCESS  read-write
     STATUS      current
     DESCRIPTION "Get or set the 802.11n physical modulation coding scheme (MCS) rate.
				Forces the N Phy transmission rate for the AP to a particular speed.
				Each group of rates corresponds to BW (20 MHz or 40 MHz) and GI (800ns or 400ns) configuration.
				mcs0:	6.5   Mbps for 20Mhz and	13.5  Mbps for 40 MHz if guard interval is 800ns.
						7.2   Mbps for 20Mhz and	15    Mbps for 40 Mhz if guard interval is 400ns.
				mcs1:	13    Mbps for 20Mhz and	27    Mbps for 40 MHz if guard interval is 800ns.
						14.4  Mbps for 20Mhz and	30    Mbps for 40 Mhz if guard interval is 400ns.
				mcs2:	19.5  Mbps for 20Mhz and	40.5  Mbps for 40 MHz if guard interval is 800ns.
						21.7  Mbps for 20Mhz and	45    Mbps for 40 Mhz if guard interval is 400ns.
				mcs3:	26    Mbps for 20Mhz and	54    Mbps for 40 MHz if guard interval is 800ns.
						28.9  Mbps for 20Mhz and	60    Mbps for 40 Mhz if guard interval is 400ns.
				mcs4:	39    Mbps for 20Mhz and	81    Mbps for 40 MHz if guard interval is 800ns.
						43.3  Mbps for 20Mhz and	90    Mbps for 40 Mhz if guard interval is 400ns.
				mcs5:	52    Mbps for 20Mhz and	108   Mbps for 40 MHz if guard interval is 800ns.
						57.8  Mbps for 20Mhz and	120   Mbps for 40 Mhz if guard interval is 400ns.
				mcs6:	58.5  Mbps for 20Mhz and	121.5 Mbps for 40 MHz if guard interval is 800ns.
						65    Mbps for 20Mhz and	135   Mbps for 40 Mhz if guard interval is 400ns.
				mcs7:	65    Mbps for 20Mhz and	135   Mbps for 40 MHz if guard interval is 800ns.
						72.2  Mbps for 20Mhz and	150   Mbps for 40 Mhz if guard interval is 400ns.
				mcs8:	13    Mbps for 20Mhz and	27    Mbps for 40 MHz if guard interval is 800ns.
						14.4  Mbps for 20Mhz and	30    Mbps for 40 Mhz if guard interval is 400ns.
				mcs9:	26    Mbps for 20Mhz and	54    Mbps for 40 MHz if guard interval is 800ns.
						28.9  Mbps for 20Mhz and	60    Mbps for 40 Mhz if guard interval is 400ns.
				mcs10:	39    Mbps for 20Mhz and	81    Mbps for 40 MHz if guard interval is 800ns.
						43.3  Mbps for 20Mhz and	90    Mbps for 40 Mhz if guard interval is 400ns.
				mcs11:	52    Mbps for 20Mhz and	108   Mbps for 40 MHz if guard interval is 800ns.
						57.8  Mbps for 20Mhz and	120   Mbps for 40 Mhz if guard interval is 400ns.
				mcs12:	78    Mbps for 20Mhz and	162   Mbps for 40 MHz if guard interval is 800ns.
						86.7  Mbps for 20Mhz and	180   Mbps for 40 Mhz if guard interval is 400ns.
				mcs13:	104   Mbps for 20Mhz and	216   Mbps for 40 MHz if guard interval is 800ns.
						115.6 Mbps for 20Mhz and	240   Mbps for 40 Mhz if guard interval is 400ns.
				mcs14:	117   Mbps for 20Mhz and	243   Mbps for 40 MHz if guard interval is 800ns.
						130.3 Mbps for 20Mhz and	270   Mbps for 40 Mhz if guard interval is 400ns.
				mcs15:	130   Mbps for 20Mhz and	270   Mbps for 40 MHz if guard interval is 800ns.
						144.4 Mbps for 20Mhz and	300   Mbps for 40 Mhz if guard interval is 400ns.
				mcs16 ~ mcs23 are also suppported.
				"
     ::= { arrisRouterWiFi80211NSettings 2 }

arrisRouterWiFiChannelBW OBJECT-TYPE
     SYNTAX      INTEGER { unknown(-1), width20MHz(0), width40MHz(1), width20and40Mhz(2) }
     MAX-ACCESS  read-write
     STATUS      current
     DESCRIPTION "Determines which Band Width that we will be operating in. Either the 20MHz or the 40MHz.
                    Note: This is for 802.11n mode only."
     ::= { arrisRouterWiFi80211NSettings 3 }

arrisRouterWiFi80211NSideBand OBJECT-TYPE
    SYNTAX      INTEGER {
        unknown(-1),
        upper(1),
        lower(2)
    }
    MAX-ACCESS  read-write
    STATUS      current
    DESCRIPTION
        "Determines which side Band the channel will operate in.
        Note: This is for 802.11n mode only, this OID is dependent of what arrisRouterWiFiChannelBW is selected and only
        applies when 40MHz is selected."
    ::= { arrisRouterWiFi80211NSettings 4 }

arrisRouterWiFiHTMode OBJECT-TYPE
     SYNTAX      INTEGER { mixed(0), greenField(1) }
     MAX-ACCESS  read-write
     STATUS      current
     DESCRIPTION "In mixed mode, each 802.11n transmission is always embedded in an 802.11a or 802.11g transmission.
                 Green field will ingore some of the early standard, so 802.11n devices have higher efficiency but 802.11a/b/g devices
                 can not use this network in greenfield mode."
     DEFVAL { 0 }
     ::= { arrisRouterWiFi80211NSettings 5 }

arrisRouterWiFiGuardInterval OBJECT-TYPE
     SYNTAX      INTEGER { gi400(0), gi800(1), auto(2) }
     MAX-ACCESS  read-write
     STATUS      current
     DESCRIPTION "Spacing between transmission of symbols in nanoseconds."
     DEFVAL { gi800 }
     ::= { arrisRouterWiFi80211NSettings 6 }

arrisRouterWiFiAMSDUEnable OBJECT-TYPE
     SYNTAX      TruthValue
     MAX-ACCESS  read-write
     STATUS      current
     DESCRIPTION "Aggregation of MAC Service Data Units (MSDUs) at the top of the MAC."
     DEFVAL { false }
     ::= { arrisRouterWiFi80211NSettings 7 }

arrisRouterWiFiDeclinePeerBA OBJECT-TYPE
     SYNTAX      TruthValue
     MAX-ACCESS  read-write
     STATUS      current
     DESCRIPTION "Enable or disable rejection of peer BA-request."
     DEFVAL { false }
     ::= { arrisRouterWiFi80211NSettings 8 }

arrisRouterWiFiBlockAck OBJECT-TYPE
     SYNTAX      TruthValue
     MAX-ACCESS  read-write
     STATUS      current
     DESCRIPTION "Enable or disable blocking of ACK (BA) during data transfer."
     DEFVAL { false }
     ::= { arrisRouterWiFi80211NSettings 9 }

arrisRouterWiFiNProtection OBJECT-TYPE
     SYNTAX      INTEGER { off(0), auto(1) }
     MAX-ACCESS  read-write
     STATUS      current
     DESCRIPTION "Set/read 802.11n protection setting. This is for OFDM protection for MIMO frames."
     ::= { arrisRouterWiFi80211NSettings 10 }

arrisRouterWiFiAllow40MHzOnlyOperation OBJECT-TYPE
     SYNTAX      TruthValue
     MAX-ACCESS  read-write
     STATUS      current
     DESCRIPTION "Allow the user to set 40 MHz only Wifi operation."
     DEFVAL { false }
     ::= { arrisRouterWiFi80211NSettings 11 }


-- This provides support for multiple Basic Service Sets (BSS)

arrisRouterBSSTable OBJECT-TYPE
      SYNTAX      SEQUENCE OF ArrisRouterBSSEntry
      MAX-ACCESS  not-accessible
      STATUS      current
      DESCRIPTION "Table contains settings for individual wireless networks (SSID)."
      ::= { arrisRouterWirelessCfg 22 }

arrisRouterBSSEntry OBJECT-TYPE
      SYNTAX      ArrisRouterBSSEntry
      MAX-ACCESS  not-accessible
      STATUS      current
      DESCRIPTION "Table contains settings for individual wireless networks (SSID)."
      INDEX { ifIndex }	--from IF-MIB
      ::= { arrisRouterBSSTable 1 }

ArrisRouterBSSEntry ::= SEQUENCE {
		arrisRouterBssID				PhysAddress,
		arrisRouterBssSSID				DisplayString,
		arrisRouterBssActive			TruthValue,
		arrisRouterBssSSIDBroadcast		TruthValue,
		arrisRouterBssSecurityMode		INTEGER,
		arrisRouterBssAccessMode		  INTEGER,
		arrisRouterBssNetworkIsolate	TruthValue,
		arrisRouterBssMACAccessCount	Unsigned32,
		arrisRouterBssMACAccessClear	INTEGER,
		arrisRouterBSSArpAuditInterval Unsigned32,
		arrisRouterBssMaxWifiClients       INTEGER,
		arrisRouterBssWmmEnable         TruthValue,
		arrisRouterBssWmmAPSD           TruthValue,
		arrisRouterBssActiveTimeout     OCTET STRING,
		arrisRouterDefaultBssSSID       DisplayString,
		arrisRouterBssStaSteeringEnable   TruthValue,
		arrisRouterWiFiRSSIThreshold                    Integer32,
		arrisRouterWiFiRSSIThresholdEnable              TruthValue,
		arrisRouterWiFiRSSIThresholdRefusedCount        INTEGER,
		arrisRouterBSSEnterpriseCfg                     Unsigned32,
		arrisRouterWiFiClientHighWatermarkThreshold         Unsigned32,
		arrisRouterWiFiClientHighWatermarkThresholdReached  Unsigned32,
		arrisRouterWiFiClientHighWatermark                  Unsigned32,
		arrisRouterWiFiClientHighWatermarkDate              DisplayString,
		arrisRouterBssBeaconRate                            Unsigned32,
		arrisRouterBssDisableLegacyRate                     DisplayString
		}

arrisRouterBssID OBJECT-TYPE
     SYNTAX      PhysAddress
     MAX-ACCESS  read-only
     STATUS      current
     DESCRIPTION "The physical address associated with this service set."
     ::= { arrisRouterBSSEntry 1 }

arrisRouterBssSSID OBJECT-TYPE
     SYNTAX      DisplayString (SIZE(1..64))
     MAX-ACCESS  read-write
     STATUS      current
     DESCRIPTION "The SSID for this BSS.
                  NOTE: For TS9.x, this mib only supports (1..32)."
     ::= { arrisRouterBSSEntry 2 }

arrisRouterBssActive OBJECT-TYPE
     SYNTAX      TruthValue
     MAX-ACCESS  read-write
     STATUS      current
     DESCRIPTION "Select to enable/make active this SSID."
     DEFVAL { false }
     ::= { arrisRouterBSSEntry 3 }

arrisRouterBssSSIDBroadcast OBJECT-TYPE
     SYNTAX      TruthValue
     MAX-ACCESS  read-write
     STATUS      current
     DESCRIPTION "Select to broadcast or not this SSID.  It is somewhat more secure to NOT broadcast the SSID."
     DEFVAL { true }
     ::= { arrisRouterBSSEntry 4 }

arrisRouterBssSecurityMode OBJECT-TYPE
     SYNTAX      INTEGER { disabled(0),
                            wep(1),
                            wpaPsk(2),
                            wpa2Psk(3),
                            wpaEnterprise(4),
                            wpa2Enterprise(5),
                            wepEnterprise(6),
                            wpaWpa2Psk(7),
                            wpaWpa2Enterprise(8),
                            wepApplyImmediate(129),
                            wpaPskImmediate(130),
                            wpa2PskImmediate(131),
                            wpaEnterpriseImmediate(132),
                            wpa2EnterpriseImmediate(133),
                            wepEnterpriseImmediate(134),
                            wpaWpa2PskImmediate(135),
                            wpaWpa2EnterpriseImmediate(136)
                            }
     MAX-ACCESS  read-write
     STATUS      current
     DESCRIPTION "The security mode. The arrisRouterWpsMode or arrisRouterWps50Mode will be set to disabled(0) when the primary SSID security mode set to wep(1).
     To force this value to be applied immediately set bit 8 high."
     ::= { arrisRouterBSSEntry 5 }

arrisRouterBssAccessMode OBJECT-TYPE
    SYNTAX      INTEGER {
                allowAny(1),
                allowList(2),
                denyList(3)
    }
    MAX-ACCESS  read-write
    STATUS      current
    DESCRIPTION
        "Controls what stations will be given access to the device.  If set to
         allowAny(1), then any station will be allowed to connect.  If set
         to restrictToList(2), then only stations whose MAC address appears in
         the arrisRouterMACAccessTable will be allowed to connect.  If set to
         denyList(3), any station will be allowed to connect except those in
         the arrisRouterMACAccessTable."
    ::= { arrisRouterBSSEntry 6 }

arrisRouterBssNetworkIsolate OBJECT-TYPE
    SYNTAX      TruthValue
    MAX-ACCESS  read-write
    STATUS      current
    DESCRIPTION
        "If set to true, this service set will
         have access to the wide area internet, but will have restricted access
         to the local area network.  If set to false, this service set will be authorized as a full member of
         the local area network."
	DEFVAL { false }
    ::= { arrisRouterBSSEntry 7 }

arrisRouterBssMACAccessCount  OBJECT-TYPE
    SYNTAX      Unsigned32
    MAX-ACCESS  read-only
    STATUS      current
    DESCRIPTION "Current count of items in the MACAccessTable."
    ::= { arrisRouterBSSEntry 8 }

arrisRouterBssMACAccessClear  OBJECT-TYPE
    SYNTAX      INTEGER { clear(1) }
    MAX-ACCESS  read-write
    STATUS      current
    DESCRIPTION "Set to clear(1) to clear the entire list of MAC addresses in arrisRouterMACAccessTable."
    ::= { arrisRouterBSSEntry 9 }

arrisRouterBSSArpAuditInterval OBJECT-TYPE
    SYNTAX      Unsigned32
    UNITS       "seconds"
    MAX-ACCESS  read-write
    STATUS      current
    DESCRIPTION
        "Sets the ARP audit interval for periodical checking all ARP entries under this SSID whether the entry is still valid.
         If set to zero, periodicical checking is disabled for this SSID."
    ::= { arrisRouterBSSEntry 10 }

arrisRouterBssMaxWifiClients OBJECT-TYPE
     SYNTAX      INTEGER
     MAX-ACCESS  read-write
     STATUS      current
     DESCRIPTION "The maximum  number of concurrent wifi clients for this AP.
                  0 means no limit"
     DEFVAL  { 0 }
     ::= { arrisRouterBSSEntry 11 }

arrisRouterBssWmmEnable OBJECT-TYPE
     SYNTAX      TruthValue
     MAX-ACCESS  read-write
     STATUS      current
     DESCRIPTION "Enable/disable WMM(Wi-Fi Multimedia) based on SSID."
     DEFVAL { true }
     ::= { arrisRouterBSSEntry 12 }

arrisRouterBssWmmAPSD OBJECT-TYPE
     SYNTAX      TruthValue
     MAX-ACCESS  read-write
     STATUS      current
     DESCRIPTION "Enable/disable WMM APSD(Wi-Fi Multimedia Automatic Power Save Delivery) based on SSID."
     DEFVAL { true }
     ::= { arrisRouterBSSEntry 13 }

arrisRouterBssActiveTimeout OBJECT-TYPE
     SYNTAX      OCTET STRING (SIZE (1..16))
     MAX-ACCESS  read-write
     STATUS      current
     DESCRIPTION "Indicates the time and date when the BSS will be disabled. The configured time and date must be after the current TOD.The format is: dd/mm/yyyy-hh:mm.(e.g: 29/10/2014-18:36)"
     ::= { arrisRouterBSSEntry 14 }

arrisRouterDefaultBssSSID OBJECT-TYPE
     SYNTAX      DisplayString (SIZE(1..32))
     MAX-ACCESS  read-only
     STATUS      current
     DESCRIPTION "The default SSID (Service Set Identifier) set from the factory."
     ::= { arrisRouterBSSEntry 15 }

arrisRouterBssStaSteeringEnable OBJECT-TYPE
     SYNTAX      TruthValue
     MAX-ACCESS  read-write
     STATUS      current
     DESCRIPTION "Enable/disable STA Steering for this BSS."
     DEFVAL { false }
     ::= { arrisRouterBSSEntry 16 }

arrisRouterWiFiRSSIThreshold OBJECT-TYPE
     SYNTAX      Integer32 (-127..128)
     MAX-ACCESS  read-write
     STATUS      current
     DESCRIPTION  "Provide ability to disallow clients to associate if the RSSI level falls below a configured threshold The default value of the RSSI Threshold is 0 dBm."
     DEFVAL { 0 }
     ::= { arrisRouterBSSEntry 17 }

arrisRouterWiFiRSSIThresholdEnable OBJECT-TYPE
     SYNTAX      TruthValue
     MAX-ACCESS  read-write
     STATUS      current
     DESCRIPTION  "Provide ability to ENABLE/DISABLE  RSSI Threshold ."
     DEFVAL { false }
     ::= { arrisRouterBSSEntry 18 }

arrisRouterWiFiRSSIThresholdRefusedCount OBJECT-TYPE
     SYNTAX      INTEGER
     MAX-ACCESS  read-only
     STATUS      current
     DESCRIPTION  " Get Association Refused Count when RSSL is lower than  RSSI Threshold ."
     DEFVAL { 0 }
     ::= { arrisRouterBSSEntry 19 }

arrisRouterBSSEnterpriseCfg OBJECT-TYPE
     SYNTAX      Unsigned32
     MAX-ACCESS  read-write
     STATUS      current
     DESCRIPTION
          "Enable or disable Enterprise Features on This BSS
           Bit 0 = Enable/ Disable -- 0 = Disable (overrides all other settings)
           Bit 1 = Per BSS Beacon Settings (arrisRouterBSSBeaconCfgTable)
           Bit 2 = Per BSS Rate Settings (arrisRouterBSSRateCfgTable)
           Bit 3 = Per BSS Management Frame Power (arrisRouterBSSPowerTable)"
     DEFVAL { 0 }
     ::= { arrisRouterBSSEntry 20 }

arrisRouterWiFiClientHighWatermarkThreshold OBJECT-TYPE
     SYNTAX      Unsigned32  (0..50)
     MAX-ACCESS  read-write
     STATUS      current
     DESCRIPTION  "The HighWatermarkThreshold value that is lesser than or equal to MaxAssociatedDevices.Setting this parameter does not actually limit the number of clients that can associate with this access point as that is controlled by MaxAssociatedDevices.  MaxAssociatedDevices or 50. The default value of this parameter should be equal to MaxAssociatedDevices. In case MaxAssociatedDevices is 0 (zero), the default value of this parameter should be 50. A value of 0 means that there is no specific limit and Watermark calculation algorithm should be turned off."
     DEFVAL { 0 }
     ::= { arrisRouterBSSEntry 21 }

arrisRouterWiFiClientHighWatermarkThresholdReached OBJECT-TYPE
     SYNTAX      Unsigned32
     MAX-ACCESS  read-only
     STATUS      current
     DESCRIPTION  "Number of times the current total number of associated device has reached the HighWatermarkThreshold value."
     DEFVAL { 0 }
     ::= { arrisRouterBSSEntry 22 }

arrisRouterWiFiClientHighWatermark OBJECT-TYPE
     SYNTAX      Unsigned32
     MAX-ACCESS  read-only
     STATUS      current
     DESCRIPTION  "Maximum number of associated devices that have ever associated with the access point."
     DEFVAL { 0 }
     ::= { arrisRouterBSSEntry 23 }

arrisRouterWiFiClientHighWatermarkDate OBJECT-TYPE
     SYNTAX      DisplayString
     MAX-ACCESS  read-only
     STATUS      current
     DESCRIPTION  "Date and Time at which the maximum number of associated devices ever associated with the access point concurrenlty
                  since the last reset of the device or WiFi module."
     ::= { arrisRouterBSSEntry 24 }

arrisRouterBssBeaconRate OBJECT-TYPE
     SYNTAX      Unsigned32
     MAX-ACCESS  read-write
     STATUS      current
     DESCRIPTION "Configure the beacon rates per SSID"
     DEFVAL { 1000 }
     ::= { arrisRouterBSSEntry 25 }

arrisRouterBssDisableLegacyRate OBJECT-TYPE
     SYNTAX       DisplayString (SIZE(0..255))
     MAX-ACCESS   read-write
     STATUS       current
     DESCRIPTION  "Disable the specific Legacy Rate"
     ::= { arrisRouterBSSEntry 26 }

-- WEP configuration data if wep or wepEnterprise is selected security mode

arrisRouterWEPTable OBJECT-TYPE
      SYNTAX      SEQUENCE OF ArrisRouterWEPEntry
      MAX-ACCESS  not-accessible
      STATUS      current
      DESCRIPTION "Table contains settings for wireless networks."
      ::= { arrisRouterWirelessCfg 23 }

arrisRouterWEPEntry OBJECT-TYPE
      SYNTAX      ArrisRouterWEPEntry
      MAX-ACCESS  not-accessible
      STATUS      current
      DESCRIPTION "Table contains settings for wireless networks."
      INDEX { ifIndex }
      ::= { arrisRouterWEPTable 1 }

ArrisRouterWEPEntry ::= SEQUENCE {
    arrisRouterWEPCurrentKey			Unsigned32,
    arrisRouterWEPEncryptionMode		INTEGER,
    arrisRouterWEPPassPhrase			DisplayString
    }


arrisRouterWEPCurrentKey OBJECT-TYPE
    SYNTAX      Unsigned32
    MAX-ACCESS  read-write
    STATUS      current
    DESCRIPTION
        "Controls and reflects the default key which will be used when 64 or
         128 bit encryption is enabled.  Indicates the entry from the
         arrisRouterWEP64BitKeyTable if arrisRouterWEPEncryptionMode is set to wep64(1), or
         the entry from the arrisRouterWEP128BitKeyTable if arrisRouterWEPEncryptionMode
         is set to wep128(2).

         This object may only be set to indicate an active row in the
         arrisRouterWEP64BitKeyTable or arrisRouterWEP128BitKeyTable.  If the value
         corresponds to a row which does not exist or a row which is not
         active, the set will be rejected with an inconsistentValue error."
    ::= { arrisRouterWEPEntry 1 }

arrisRouterWEPEncryptionMode OBJECT-TYPE
    SYNTAX      INTEGER {
                wep64(1),
                wep128(2)
    }
    MAX-ACCESS  read-write
    STATUS      current
    DESCRIPTION
        "Selects the WEP encryption method used by this service set.
         If set to wep64(1), then 64 bit WEP encryption will be
         used with the keys from the arrisRouterWEP64BitKeyTable.  If set to
         wep128(2), then 128 bit WEP encryption will be used with keys from
         the arrisRouterWEP128BitKeyTable."
    ::= { arrisRouterWEPEntry 2 }

arrisRouterWEPPassPhrase OBJECT-TYPE
    SYNTAX      DisplayString (SIZE(0..32))
    MAX-ACCESS  read-write
    STATUS      current
    DESCRIPTION "The passphrase used for WEP security. This can be used to automatically generate the hex WEP keys."
    ::= { arrisRouterWEPEntry 3 }


arrisRouterWEP64BitKeyTable OBJECT-TYPE
    SYNTAX      SEQUENCE OF ArrisRouterWEP64BitKeyEntry
    MAX-ACCESS  not-accessible
    STATUS      current
    DESCRIPTION "A table of 40 bit key values used when operating in WEP 64 mode."
    ::= { arrisRouterWirelessCfg 24 }

arrisRouterWEP64BitKeyEntry OBJECT-TYPE
    SYNTAX      ArrisRouterWEP64BitKeyEntry
    MAX-ACCESS  not-accessible
    STATUS      current
    DESCRIPTION
        "A key to be used by the row in the arrisRouterBSSTable identified by the
         value of ifIndex in the row index."
    INDEX   { ifIndex, arrisRouterWEP64BitKeyIndex }
    ::= { arrisRouterWEP64BitKeyTable 1 }

ArrisRouterWEP64BitKeyEntry ::=
    SEQUENCE    {
                arrisRouterWEP64BitKeyIndex           Integer32,
                arrisRouterWEP64BitKeyValue           DisplayString,
                arrisRouterWEP64BitKeyStatus          RowStatus
    }

arrisRouterWEP64BitKeyIndex OBJECT-TYPE
    SYNTAX      Integer32 (1..4)
    MAX-ACCESS  not-accessible
    STATUS      current
    DESCRIPTION
        "Identifies an instance of a key among those used by the service set
         identified by the value of ifIndex in the row index."
    ::= { arrisRouterWEP64BitKeyEntry 1 }

arrisRouterWEP64BitKeyValue OBJECT-TYPE
    SYNTAX      DisplayString
    MAX-ACCESS  read-create
    STATUS      current
    DESCRIPTION
        "A 40 bit key to be used when the corresponding instance of
         arrisRouterWiFiSecurityMode is set to wep(1) and the corresponding instance
         of arrisRouterWEPEncryptionMode is set to wep64(1)."
    ::= { arrisRouterWEP64BitKeyEntry 2 }

arrisRouterWEP64BitKeyStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterWEP64BitKeyStatus column is 'notReady'.

         In particular, a newly created row cannot be made active until the
         corresponding instance of arrisRouterWEP64BitKeyValue has been set.

         Only rows with a status of active(1) will be applied.

         This object may not be set to a value of notInService(2) or destroy(6)
         if the corresponding instance of arrisRouterWEPDefaultKey identifies
         this row as they current key in use.  Such an attempt will be rejected
         with an inconsistentValue error."
    ::= { arrisRouterWEP64BitKeyEntry 3 }


arrisRouterWEP128BitKeyTable OBJECT-TYPE
    SYNTAX      SEQUENCE OF ArrisRouterWEP128BitKeyEntry
    MAX-ACCESS  not-accessible
    STATUS      current
    DESCRIPTION
        "A table of 104 bit key values used when operating in WEP 128 mode."
    ::= { arrisRouterWirelessCfg 25 }

arrisRouterWEP128BitKeyEntry OBJECT-TYPE
    SYNTAX      ArrisRouterWEP128BitKeyEntry
    MAX-ACCESS  not-accessible
    STATUS      current
    DESCRIPTION
        "A key to be used by the row in the arrisRouterBSSTable identified by the
         value of ifIndex in the row index."
    INDEX   { ifIndex, arrisRouterWEP128BitKeyIndex }
    ::= { arrisRouterWEP128BitKeyTable 1 }

ArrisRouterWEP128BitKeyEntry ::=
    SEQUENCE    {
                arrisRouterWEP128BitKeyIndex           Integer32,
                arrisRouterWEP128BitKeyValue           DisplayString,
                arrisRouterWEP128BitKeyStatus          RowStatus
    }

arrisRouterWEP128BitKeyIndex OBJECT-TYPE
    SYNTAX      Integer32 (1..4)
    MAX-ACCESS  not-accessible
    STATUS      current
    DESCRIPTION
        "Identifies an instance of a key among those used by the service set
         identified by the value of ifIndex in the row index."
    ::= { arrisRouterWEP128BitKeyEntry 1 }

arrisRouterWEP128BitKeyValue OBJECT-TYPE
    SYNTAX      DisplayString
    MAX-ACCESS  read-create
    STATUS      current
    DESCRIPTION
        "A 104 bit key to be used when the corresponding instance of
         arrisRouterWiFiSecurityMode is set to wep(1) and the corresponding instance
         of arrisRouterWEPEncryptionMode is set to wep128(128)."
    ::= { arrisRouterWEP128BitKeyEntry 2 }

arrisRouterWEP128BitKeyStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterWEP128BitKeyStatus column is 'notReady'.

         In particular, a newly created row cannot be made active until the
         corresponding instance of arrisRouterWEP128BitKeyValue has been set.

         Only rows with a status of active(1) will be applied.

         This object may not be set to a value of notInService(2) or destroy(6)
         if the corresponding instance of arrisRouterWEPDefaultKey identifies
         this row as they current key in use.  Such an attempt will be rejected
         with an inconsistentValue error."
    ::= { arrisRouterWEP128BitKeyEntry 3 }



-- Objects used to control WPA based security modes

arrisRouterWPATable   OBJECT-TYPE
    SYNTAX      SEQUENCE OF ArrisRouterWPAEntry
    MAX-ACCESS  not-accessible
    STATUS      current
    DESCRIPTION
        "A table used to configure settings related to the WPA security modes."
    ::= { arrisRouterWirelessCfg 26 }

arrisRouterWPAEntry OBJECT-TYPE
    SYNTAX      ArrisRouterWPAEntry
    MAX-ACCESS  not-accessible
    STATUS      current
    DESCRIPTION
        "An entry defining the WPA characteristics of an individual service set.
         A row exists in this table for each row in the arrisRouterBSSTable for which
         arrisRouterWiFiSecurityMode is set to wpaPsk(2), wpa2Psk(3), wpaEnterprise(4),
         or wpa2Enterprise(5)."
    INDEX   { ifIndex  }
    ::= { arrisRouterWPATable 1 }

ArrisRouterWPAEntry ::=
    SEQUENCE    {
                arrisRouterWPAAlgorithm            INTEGER,
                arrisRouterWPAPreSharedKey         OCTET STRING,
                arrisRouterWPAGroupRekeyInterval   Unsigned32,
                arrisRouterWPAReAuthInterval	   Unsigned32,
                arrisRouterWPAPreAuthEnable        TruthValue,
                arrisRouterDefaultWPAPreSharedKey  OCTET STRING
    }

arrisRouterWPAAlgorithm OBJECT-TYPE
    SYNTAX      INTEGER {
                tkip(1),
                aes(2),
                tkipPlusAes(3)
    }
    MAX-ACCESS  read-write
    STATUS      current
    DESCRIPTION
        "Controls and reflects the WPA encryption mode used by the service set.
         The WPA algorithm for WPA-PSK and WPA-Enterprise security mode is either
         tkip(1) or aes(2).

         The WPA algorithm for WPA2-PSK and WPA2-Enterprise security mode is either
         aes(2) or tkipPlusAes(3)."
    ::= { arrisRouterWPAEntry 1 }

arrisRouterWPAPreSharedKey OBJECT-TYPE
    SYNTAX      OCTET STRING (SIZE (8..64))
    MAX-ACCESS  read-write
    STATUS      current
    DESCRIPTION
        "Sets the WPA Pre-Shared Key (PSK) used by this service set.  This
         value MUST be either a 64 byte hexadecimal number, OR an 8 to 63
         character ASCII string."
    ::= { arrisRouterWPAEntry 2 }

arrisRouterWPAGroupRekeyInterval OBJECT-TYPE
    SYNTAX      Unsigned32 (0..1048575)
    UNITS       "seconds"
    MAX-ACCESS  read-write
    STATUS      current
    DESCRIPTION
        "Sets the WPA Group Rekey Interval for this service set. If set to zero,
         periodic rekeying is disabled for this service set."
    ::= { arrisRouterWPAEntry 3 }

arrisRouterWPAReAuthInterval OBJECT-TYPE
    SYNTAX      Unsigned32
    UNITS       "seconds"
    MAX-ACCESS  read-write
    STATUS      current
    DESCRIPTION
        "Sets the WPA Group reauthentication interval for this service set. If set to zero,
         it is disabled for this service set."
    ::= { arrisRouterWPAEntry 4 }

arrisRouterWPAPreAuthEnable OBJECT-TYPE
    SYNTAX      TruthValue
    MAX-ACCESS  read-write
    STATUS      current
    DESCRIPTION
        "Enable or disable WPA2 pre-authentication.
         In preauthentication, a WPA2 wireless client can perform an 802.1X authentication with other wireless access points
         in its range when it is still connected to its current wireless access point."
	DEFVAL { false }
    ::= { arrisRouterWPAEntry 5 }

arrisRouterDefaultWPAPreSharedKey OBJECT-TYPE
    SYNTAX      OCTET STRING (SIZE (8..64))
    MAX-ACCESS  read-only
    STATUS      current
    DESCRIPTION
        "The default Wi-Fi passphrase set from the factory."
    ::= { arrisRouterWPAEntry 6  }

-- Objects used to control RADIUS based security modes

arrisRouterRadiusTable   OBJECT-TYPE
    SYNTAX      SEQUENCE OF ArrisRouterRadiusEntry
    MAX-ACCESS  not-accessible
    STATUS      current
    DESCRIPTION
        "A table used to configure settings related to the RADIUS security
         modes, including WPA-Enterprise, WPA2-Enterprise and RADIUS-WEP."
    ::= { arrisRouterWirelessCfg 27 }

arrisRouterRadiusEntry OBJECT-TYPE
    SYNTAX      ArrisRouterRadiusEntry
    MAX-ACCESS  not-accessible
    STATUS      current
    DESCRIPTION
         "An entry defining the RADIUS characteristics of an individual service
          set.  A row exists in this table for each row in the arrisRouterBSSTable
          for which arrisRouterWiFiSecurityMode is set to wpaEnterprise(4),
          wpa2Enterprise(5), or radiusWep(6)."
    INDEX   { ifIndex }
    ::= { arrisRouterRadiusTable 1 }

ArrisRouterRadiusEntry ::=
    SEQUENCE    {
                arrisRouterRadiusAddressType       InetAddressType,
                arrisRouterRadiusAddress           InetAddress,
                arrisRouterRadiusPort              Unsigned32,
                arrisRouterRadiusKey               DisplayString,
                arrisRouterRadiusReAuthInterval    Unsigned32
    }

arrisRouterRadiusAddressType OBJECT-TYPE
    SYNTAX      InetAddressType
    MAX-ACCESS  read-write
    STATUS      current
    DESCRIPTION
        "The type of internet address used for arrisRouterRadiusAddress."
    ::= { arrisRouterRadiusEntry 1 }

arrisRouterRadiusAddress OBJECT-TYPE
    SYNTAX      InetAddress
    MAX-ACCESS  read-write
    STATUS      current
    DESCRIPTION
        "The internet address of the RADIUS server for this service set."
    ::= { arrisRouterRadiusEntry 2 }

arrisRouterRadiusPort OBJECT-TYPE
    SYNTAX      Unsigned32
    MAX-ACCESS  read-write
    STATUS      current
    DESCRIPTION
        "The UDP port used to communicate with the RADIUS server for this
         service set."
    ::= { arrisRouterRadiusEntry 3 }

arrisRouterRadiusKey OBJECT-TYPE
    SYNTAX      DisplayString (SIZE(1..64))
    MAX-ACCESS  read-write
    STATUS      current
    DESCRIPTION
        "The RADIUS key."
    ::= { arrisRouterRadiusEntry 4 }

arrisRouterRadiusReAuthInterval OBJECT-TYPE
    SYNTAX      Unsigned32
    UNITS       "seconds"
    MAX-ACCESS  read-write
    STATUS      current
    DESCRIPTION
        "The network re-authentication interval.  If set to zero, no
         re-authentication will be performed."
    ::= { arrisRouterRadiusEntry 5 }


arrisRouterMACAccessTable  OBJECT-TYPE
    SYNTAX      SEQUENCE OF ArrisRouterMACAccessEntry
    MAX-ACCESS  not-accessible
    STATUS      current
    DESCRIPTION
        "A table of MAC addresses which defines the MAC address based access
         restrictions for the system."
    ::= { arrisRouterWirelessCfg 28 }

arrisRouterMACAccessEntry OBJECT-TYPE
    SYNTAX      ArrisRouterMACAccessEntry
    MAX-ACCESS  not-accessible
    STATUS      current
    DESCRIPTION
        "A row in the table which specifies a single MAC address for a given
         service set."
    INDEX   { ifIndex, arrisRouterMACAccessIndex }
    ::= { arrisRouterMACAccessTable 1 }

ArrisRouterMACAccessEntry ::=
    SEQUENCE    {
                arrisRouterMACAccessIndex       Integer32,
                arrisRouterMACAccessAddr	MacAddress,
                arrisRouterMACAccessStatus      RowStatus,
                arrisRouterMACAccessDeviceName  DisplayString
    }

arrisRouterMACAccessIndex OBJECT-TYPE
    SYNTAX      Integer32 (1..32)
    MAX-ACCESS  not-accessible
    STATUS      current
    DESCRIPTION
        "Indicates the instance of this table row."
    ::= { arrisRouterMACAccessEntry 1 }

arrisRouterMACAccessAddr OBJECT-TYPE
    SYNTAX      MacAddress
    MAX-ACCESS  read-create
    STATUS      current
    DESCRIPTION
        "A MAC address of a station which will be allowed to connect to the
         service set if arrisRouterBssAccessMode is set to restrictToList(2), or
         forbidden if arrisRouterBssAccessMode is set to denyList(3)."
    ::= { arrisRouterMACAccessEntry 2 }

arrisRouterMACAccessStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterMACAccessStatus column is 'notReady'.

         In particular, a newly created row cannot be made active until the
         corresponding instance of arrisRouterMACAccessAddr has been set.

         Only rows with a status of active(1) will be applied."
    ::= { arrisRouterMACAccessEntry 3 }

arrisRouterMACAccessDeviceName OBJECT-TYPE
     SYNTAX      DisplayString
     MAX-ACCESS  read-create
     STATUS      current
     DESCRIPTION "A name associated with device MAC which will be allowed to connect to the
         service set if arrisRouterBssAccessMode is set to restrictToList(2), or
         forbidden if arrisRouterBssAccessMode is set to denyList(3).
	 NOTE: For TS7.x, this mib only supports (0..64)."
     ::= { arrisRouterMACAccessEntry 4 }

arrisRouterWMMCfg			 OBJECT IDENTIFIER ::= { arrisRouterWirelessCfg 29 }

arrisRouterWMMEnable OBJECT-TYPE
    SYNTAX      TruthValue
    MAX-ACCESS  read-write
    STATUS      current
    DESCRIPTION "Enable/disable WiFi MultiMedia (WMM) QOS support.. Note that this applies to only the primary (zero) Wireless network."
    DEFVAL { true }
    ::= { arrisRouterWMMCfg 1 }

arrisRouterWMMNoAck OBJECT-TYPE
    SYNTAX      TruthValue
    MAX-ACCESS  read-write
    STATUS      current
    DESCRIPTION "This refers to the acknowledge policy used at the MAC level.
                Enabling no-acknowledgement can result in more efficient throughput but
                higher error rates in a noisy Radio Frequency (RF) environment."
    DEFVAL { false }
    ::= { arrisRouterWMMCfg 2 }

arrisRouterWMMAPSD OBJECT-TYPE
    SYNTAX      TruthValue
    MAX-ACCESS  read-write
    STATUS      current
    DESCRIPTION "Automatic Power Save Delivery is a more efficient power management method than legacy 802.11 Power Save Polling.
                Set the value here."
    DEFVAL { true }
    ::= { arrisRouterWMMCfg 3 }

arrisRouterWMMEDCAAPTable  OBJECT-TYPE
    SYNTAX      SEQUENCE OF ArrisRouterWMMEDCAAPEntry
    MAX-ACCESS  not-accessible
    STATUS      current
    DESCRIPTION "A table of for setting WMM EDCA values for the access point.
                This affects traffic flowing from the access point to the client station "
    ::= { arrisRouterWMMCfg 4 }

arrisRouterWMMEDCAAPEntry OBJECT-TYPE
    SYNTAX      ArrisRouterWMMEDCAAPEntry
    MAX-ACCESS  not-accessible
    STATUS      current
    DESCRIPTION "A table of for setting WMM EDCA values for the access point.
                This affects traffic flowing from the access point to the client station "
    INDEX   { arrisRouterWMMEDCAAPIndex }
    ::= { arrisRouterWMMEDCAAPTable 1 }

ArrisRouterWMMEDCAAPEntry ::=
    SEQUENCE    {
                arrisRouterWMMEDCAAPIndex		Integer32,
                arrisRouterWMMEDCAAPCWmin		Unsigned32,
                arrisRouterWMMEDCAAPCWmax		Unsigned32,
                arrisRouterWMMEDCAAPAIFSN		Unsigned32,
                arrisRouterWMMEDCAAPTxOpBLimit		Unsigned32,
                arrisRouterWMMEDCAAPTxOpAGLimit		Unsigned32,
                arrisRouterWMMEDCAAPAdmitCont		TruthValue,
                arrisRouterWMMEDCAAPDiscardOld		TruthValue
    }

arrisRouterWMMEDCAAPIndex OBJECT-TYPE
    SYNTAX      Integer32 (1..4)
    MAX-ACCESS  not-accessible
    STATUS      current
    DESCRIPTION "The index into the table will be one of the parameters: 1=ACBE (best effort), 2=ACBK (background), 3=ACVI (video), 4=ACVO (voice)"
    ::= { arrisRouterWMMEDCAAPEntry 1 }

arrisRouterWMMEDCAAPCWmin OBJECT-TYPE
    SYNTAX      Unsigned32
    UNITS		"milliseconds"
    MAX-ACCESS  read-write
    STATUS      current
	DESCRIPTION "Minimum Contention Window.
				 This parameter is input to the algorithm that determines the initial random backoff wait time (window) for retry of a transmission.
				 The value specified here in the Minimum Contention Window is the upper limit of a range from which the initial random backoff
				 wait time is determined. The first random number generated will be a number between 0 and the number specified here.
				 If the first random backoff wait time expires before the data frame is sent, a retry counter is incremented and the
				 random backoff value (window) is doubled. Doubling will continue until the size of the random backoff value reaches the number
				 defined in the Maximum Contention Window.
				 Valid values are 1, 3, 7, 15, 31, 63, 127, 255, and 511.
				 This value must be lower than the value for arrisRouterWMMEDCAAPCWmax."
    ::= { arrisRouterWMMEDCAAPEntry 2 }

arrisRouterWMMEDCAAPCWmax OBJECT-TYPE
    SYNTAX      Unsigned32
    UNITS		"milliseconds"
    MAX-ACCESS  read-write
    STATUS      current
    DESCRIPTION "Maximum Contention Window. The value specified here in the Maximum Contention Window is the upper limit for the
				 doubling of the random backoff value. This doubling continues until either the data frame is sent or the
				 Maximum Contention Window size is reached. Once the Maximum Contention Window size is reached, retries
				 will continue until a maximum number of retries allowed is reached.
				 Valid values are 1, 3, 7, 15, 31, 63, 127, 255, 511, and 1023.
				 This value must be higher than the value for arrisRouterWMMEDCAAPCWmin."
    ::= { arrisRouterWMMEDCAAPEntry 3 }

arrisRouterWMMEDCAAPAIFSN OBJECT-TYPE
    SYNTAX      Unsigned32
    UNITS		"milliseconds"
    MAX-ACCESS  read-write
    STATUS      current
    DESCRIPTION "The Arbitration Inter-Frame Spacing Number specifies a wait time for data frames."
    ::= { arrisRouterWMMEDCAAPEntry 4 }

arrisRouterWMMEDCAAPTxOpBLimit OBJECT-TYPE
    SYNTAX      Unsigned32 (0..65535)
    UNITS		"microseconds"
    MAX-ACCESS  read-write
    STATUS      current
    DESCRIPTION "Transmission Opportunity for b mode is an interval of time when a WME AP has the right to initiate
                transmissions onto the wireless medium (WM). This value specifies the Transmission Opportunity (TXOP) for AP;
                that is, the interval of time when the WMM AP has the right to initiate transmissions on the wireless network."
    ::= { arrisRouterWMMEDCAAPEntry 5 }

arrisRouterWMMEDCAAPTxOpAGLimit OBJECT-TYPE
    SYNTAX      Unsigned32 (0..65535)
    UNITS		"microseconds"
    MAX-ACCESS  read-write
    STATUS      current
    DESCRIPTION "Transmission Opportunity for A and G mode is an interval of time when a WME AP has the right to initiate
                transmissions onto the wireless medium (WM). This value specifies the Transmission Opportunity (TXOP) for AP;
                that is, the interval of time when the WMM AP has the right to initiate transmissions on the wireless network."
    ::= { arrisRouterWMMEDCAAPEntry 6 }

arrisRouterWMMEDCAAPAdmitCont OBJECT-TYPE
    SYNTAX      TruthValue
    MAX-ACCESS  read-write
    STATUS      current
    DESCRIPTION "Enable/disable admission control for specific category of traffic."
    ::= { arrisRouterWMMEDCAAPEntry 7 }

arrisRouterWMMEDCAAPDiscardOld OBJECT-TYPE
    SYNTAX      TruthValue
    MAX-ACCESS  read-write
    STATUS      current
    DESCRIPTION "Discard oldest packet first enable/disable."
    ::= { arrisRouterWMMEDCAAPEntry 8 }



arrisRouterWMMEDCASTATable  OBJECT-TYPE
    SYNTAX      SEQUENCE OF ArrisRouterWMMEDCASTAEntry
    MAX-ACCESS  not-accessible
    STATUS      current
    DESCRIPTION "A table of for setting WMM EDCA values for the access point.
                This affects traffic flowing from the client station to the access point."
    ::= { arrisRouterWMMCfg 5 }

arrisRouterWMMEDCASTAEntry OBJECT-TYPE
    SYNTAX      ArrisRouterWMMEDCASTAEntry
    MAX-ACCESS  not-accessible
    STATUS      current
    DESCRIPTION "A table of for setting WMM EDCA values for the access point.
                This affects traffic flowing from the client station to the access point."
    INDEX   { arrisRouterWMMEDCASTAIndex }
    ::= { arrisRouterWMMEDCASTATable 1 }

ArrisRouterWMMEDCASTAEntry ::=
    SEQUENCE    {
                arrisRouterWMMEDCASTAIndex		Integer32,
                arrisRouterWMMEDCASTACWmin		Unsigned32,
                arrisRouterWMMEDCASTACWmax		Unsigned32,
                arrisRouterWMMEDCASTAAIFSN		Unsigned32,
                arrisRouterWMMEDCASTATxOpBLimit		Unsigned32,
                arrisRouterWMMEDCASTATxAGLimit		Unsigned32
    }

arrisRouterWMMEDCASTAIndex OBJECT-TYPE
    SYNTAX      Integer32 (1..4)
    MAX-ACCESS  not-accessible
    STATUS      current
    DESCRIPTION "The index into the table will be one of the paramaters: 1-ACBE (best effort), 2-ACBK (background), 3-ACVI (video), 4-ACVO (voice)"
    ::= { arrisRouterWMMEDCASTAEntry 1 }

arrisRouterWMMEDCASTACWmin OBJECT-TYPE
    SYNTAX      Unsigned32
    UNITS		"milliseconds"
    MAX-ACCESS  read-write
    STATUS      current
    DESCRIPTION "Minimum Contention Window.
                 This parameter is input to the algorithm that determines the initial random backoff wait time (window) for retry of a transmission.
                 The value specified here in the Minimum Contention Window is the upper limit of a range from which the initial random backoff
                 wait time is determined. The first random number generated will be a number between 0 and the number specified here.
                 If the first random backoff wait time expires before the data frame is sent, a retry counter is incremented and the
                 random backoff value (window) is doubled. Doubling will continue until the size of the random backoff value reaches the number
                 Valid values are 1, 3, 7, 15, 31, 63, 127, 255, or 511.
                 This value must be lower than the value for arrisRouterWMMEDCASTACWmax"
    ::= { arrisRouterWMMEDCASTAEntry 2 }

arrisRouterWMMEDCASTACWmax OBJECT-TYPE
    SYNTAX      Unsigned32
    UNITS		"milliseconds"
    MAX-ACCESS  read-write
    STATUS      current
    DESCRIPTION "Maximum Contention Window. The value specified here in the Maximum Contention Window is the upper limit for the
                 doubling of the random backoff value. This doubling continues until either the data frame is sent or the
                 Maximum Contention Window size is reached. Once the Maximum Contention Window size is reached, retries
                 will continue until a maximum number of retries allowed is reached.
                 Valid values are 1, 3, 7, 15, 31, 63, 127, 255, 511, or 1023.
                 This value must be higher than the value for arrisRouterWMMEDCASTACWmin."
    ::= { arrisRouterWMMEDCASTAEntry 3 }

arrisRouterWMMEDCASTAAIFSN OBJECT-TYPE
    SYNTAX      Unsigned32
    UNITS		"milliseconds"
    MAX-ACCESS  read-write
    STATUS      current
    DESCRIPTION "The Arbitration Inter-Frame Spacing Number specifies a wait time for data frames."
    ::= { arrisRouterWMMEDCASTAEntry 4 }

arrisRouterWMMEDCASTATxOpBLimit OBJECT-TYPE
    SYNTAX      Unsigned32 (0..65535)
    UNITS		"microseconds"
    MAX-ACCESS  read-write
    STATUS      current
    DESCRIPTION "Transmission Opportunity for b mode is an interval of time when a WME AP has the right to initiate
                transmissions onto the wireless medium (WM). This value specifies the Transmission Opportunity (TXOP) for AP;
                that is, the interval of time when the WMM AP has the right to initiate transmissions on the wireless network."
    ::= { arrisRouterWMMEDCASTAEntry 5 }

arrisRouterWMMEDCASTATxAGLimit OBJECT-TYPE
    SYNTAX      Unsigned32 (0..65535)
    UNITS		"microseconds"
    MAX-ACCESS  read-write
    STATUS      current
    DESCRIPTION "Transmission Opportunity for A and G mode is an interval of time when a WME AP has the right to initiate
                transmissions onto the wireless medium (WM). This value specifies the Transmission Opportunity (TXOP) for AP;
                that is, the interval of time when the WMM AP has the right to initiate transmissions on the wireless network."
    ::= { arrisRouterWMMEDCASTAEntry 6 }

arrisRouterWMMCurrentRadio OBJECT-TYPE
    SYNTAX      Integer32
    MAX-ACCESS  read-write
    STATUS      current
    DESCRIPTION "Select the 'active' radio that is used when setting or querying arrisRouterWMM* OIDs."
	DEFVAL { 0 }
    ::= { arrisRouterWMMCfg 6 }


arrisRouterWPSCfg			 OBJECT IDENTIFIER ::= { arrisRouterWirelessCfg 30 }

arrisRouterWpsMode OBJECT-TYPE
    SYNTAX      INTEGER { disabled(0), enabled(1) }
    MAX-ACCESS  read-write
    STATUS      current
    DESCRIPTION "Get and set whether or not WiFi Protected Setup (WPS) is enabled or disabled.
                 The WPS mode can't be set to enabled(1) when the primary SSID arrisRouterBssSecurityMode is wep(1)."
    ::= { arrisRouterWPSCfg 1 }

arrisRouterWpsConfigState OBJECT-TYPE
    SYNTAX      INTEGER { disabled(0), enabled(1) }
    MAX-ACCESS  read-write
    STATUS      current
    DESCRIPTION "Get and set the WiFi Protected Setup (WPS) config state."
    ::= { arrisRouterWPSCfg 2 }

arrisRouterWpsDevicePIN OBJECT-TYPE
    SYNTAX      DisplayString (SIZE(8))
    MAX-ACCESS  read-write
    STATUS      current
    DESCRIPTION "Get or set the WiFi Protected Setup (WPS) device PIN.  This is the PIN that is displayed to the user to input on their client device.
                 NOTE: This mib has read-only access property when Comcast uses TS7.x loads."
    ::= { arrisRouterWPSCfg 3 }

arrisRouterWpsDeviceName OBJECT-TYPE
    SYNTAX      DisplayString (SIZE(0..32))
    MAX-ACCESS  read-write
    STATUS      current
    DESCRIPTION "Name of this device.
                 NOTE: This mib has read-only access property when customers use TS9.x loads."
    ::= { arrisRouterWPSCfg 4 }

arrisRouterWpsModelName OBJECT-TYPE
    SYNTAX      DisplayString (SIZE(0..32))
    MAX-ACCESS  read-write
    STATUS      current
    DESCRIPTION "Model Name.
                 NOTE: This mib has read-only access property when customers use TS9.x loads."
    ::= { arrisRouterWPSCfg 5 }

arrisRouterWpsMfg OBJECT-TYPE
    SYNTAX      DisplayString (SIZE(0..64))
    MAX-ACCESS  read-write
    STATUS      current
    DESCRIPTION "Manufacturer string"
    ::= { arrisRouterWPSCfg 6 }

arrisRouterWpsResultStatus OBJECT-TYPE
    SYNTAX      INTEGER {
			wpsResultUnknown(-1),
			wpsResultNoneIssued(0),
			wpsResultAddClientSuccess(1),
			wpsResultAddClientFail(2),
			wpsResultAddClientAbort(3),
			wpsResultConfigApSuccess(4),
			wpsResultConfigApFail(5),
			wpsResultConfigApAbort(6),
			wpsResultOverlap(7),
			wpsResultTimedOut(8),
			wpsResultInProgress(9)
			}
    MAX-ACCESS  read-only
    STATUS      current
    DESCRIPTION  "The result status of the most recent WPS operation."
	::= { arrisRouterWPSCfg 7 }

arrisRouterWpsStatus OBJECT-TYPE
    SYNTAX      INTEGER {
			wpsUnknown(-1),
			wpsInitialState(0),
			wpsAssociatedStarted(1),
			wpsM2Sent(2),
			wpsM7Sent(3),
			wpsTimedOut(4),
			wpsMsgDone(5),
			wpsSuccessful(6),
			wpsMsgExchangeErr(7),
			wpsPushButtonOverlap(8),
			wpsAssociating(9),
			wpsPushButtonFindAP(10)
			}
    MAX-ACCESS  read-only
    STATUS      current
    DESCRIPTION  "Current status of the WPS subsystem."
	::= { arrisRouterWPSCfg 8 }

arrisRouterWpsConfigTimeout OBJECT-TYPE
    SYNTAX      INTEGER { disabled(0), enabled(1) }
    MAX-ACCESS  read-write
    STATUS      current
    DESCRIPTION "Get and set whether the WiFi Protected Setup (WPS) uses timeout."
    ::= { arrisRouterWPSCfg 9 }

arrisRouterWpsSTAPin OBJECT-TYPE
    SYNTAX      DisplayString (SIZE(8))
    MAX-ACCESS  read-write
    STATUS      current
    DESCRIPTION "Set the WiFi Protected Setup (WPS) PIN for a new station/device.  This is the PIN from a 'client' device."
    ::= { arrisRouterWPSCfg 10 }

arrisRouterWpsPushButton OBJECT-TYPE
    SYNTAX      INTEGER { unknown(0), activatePushButton(1), activatePINCfg(2), cancelWPS(3) }
    MAX-ACCESS  read-write
    STATUS      current
    DESCRIPTION "Set to 'activatePushButton' to push the virtual button on the Access Point and start the WPS push-button process.
				Set to 'activePINCfg' to start the WPS PIN process.  The client device PIN should be written to arrisRouterWpsSTAPin
				before triggering the WPS process.
				Cancel an active WPS config (started with either 1 or 2) by setting this value to 'cancelWPS'."
    ::= { arrisRouterWPSCfg 11 }

arrisRouterWpsBoardNum OBJECT-TYPE
    SYNTAX      DisplayString (SIZE(0..32))
    MAX-ACCESS  read-write
    STATUS      current
    DESCRIPTION "Sets the WPS Board Serial Number."
    ::= { arrisRouterWPSCfg 12 }

arrisRouterWpsModelNum OBJECT-TYPE
    SYNTAX      DisplayString (SIZE(0..32))
    MAX-ACCESS  read-write
    STATUS      current
    DESCRIPTION "Model Number."
    ::= { arrisRouterWPSCfg 13 }

arrisRouterWpsUUID OBJECT-TYPE
    SYNTAX      DisplayString (SIZE(0..16))
    MAX-ACCESS  read-write
    STATUS      current
    DESCRIPTION  "Sets WPS Universal Unique Identifier."
	::= { arrisRouterWPSCfg 14 }

arrisRouterWPSMethodCfg OBJECT IDENTIFIER ::= { arrisRouterWPSCfg 15 }

arrisRouterWPSMethodLabel OBJECT-TYPE
    SYNTAX      INTEGER { disabled(0), enabled(1) }
    MAX-ACCESS  read-write
    STATUS      current
    DESCRIPTION "Get and set whether or not WPS Label Method is enabled or disabled."
    ::= { arrisRouterWPSMethodCfg 1 }

arrisRouterWPSMethodPIN OBJECT-TYPE
    SYNTAX      INTEGER { disabled(0), enabled(1) }
    MAX-ACCESS  read-write
    STATUS      current
    DESCRIPTION "Get and set whether or not WPS PIN Method is enabled or disabled."
    ::= { arrisRouterWPSMethodCfg 2 }

arrisRouterWPSMethodPushButton OBJECT-TYPE
    SYNTAX      INTEGER { disabled(0), enabled(1) }
    MAX-ACCESS  read-write
    STATUS      current
    DESCRIPTION "Get and set whether or not WPS Push Button Method is enabled or disabled."
    ::= { arrisRouterWPSMethodCfg 3 }

arrisRouterWPSMethodKeypad OBJECT-TYPE
    SYNTAX      INTEGER { disabled(0), enabled(1) }
    MAX-ACCESS  read-write
    STATUS      current
    DESCRIPTION "Get and set whether or not WPS Keypad Method is enabled or disabled."
    ::= { arrisRouterWPSMethodCfg 4 }

arrisRouterWpsLockDownStatus OBJECT-TYPE
    SYNTAX      TruthValue
    MAX-ACCESS  read-write
    STATUS      current
    DESCRIPTION "Indicates the WPS Lockdown state, returns true when WPS is in lock state caused by incorrect number of PIN entries, set to false to release
                 WPS lockdown state."
    DEFVAL     { false }

    ::= { arrisRouterWPSCfg 16 }

arrisRouterWDSCfg			 OBJECT IDENTIFIER ::= { arrisRouterWirelessCfg 31 }

arrisRouterWDSEnable OBJECT-TYPE
    SYNTAX      INTEGER { disabled(0), enable(1) }
    MAX-ACCESS  read-write
    STATUS      current
    DESCRIPTION "Enable or disable Wireless Distribution Services (WDS)"
    ::= { arrisRouterWDSCfg 1 }

arrisRouterWDSTableFreeIdx OBJECT-TYPE
    SYNTAX      Integer32
    MAX-ACCESS  read-only
    STATUS      current
    DESCRIPTION "The lowest available index to that may be used to add a row instance to the arrisRouterWDSBridgeTable."
    ::= { arrisRouterWDSCfg 2 }

arrisRouterWDSBridgeTable  OBJECT-TYPE
    SYNTAX      SEQUENCE OF ArrisRouterWDSBridgeEntry
    MAX-ACCESS  not-accessible
    STATUS      current
    DESCRIPTION   "A table of MAC addresses for each wireless access point that can be bridged to this AP."
    ::= { arrisRouterWDSCfg 3 }

arrisRouterWDSBridgeEntry OBJECT-TYPE
    SYNTAX      ArrisRouterWDSBridgeEntry
    MAX-ACCESS  not-accessible
    STATUS      current
	DESCRIPTION   "A table of MAC addresses for each wireless access point that can be bridged to this AP."
    INDEX   { arrisRouterWDSBridgeIndex }
    ::= { arrisRouterWDSBridgeTable 1 }

ArrisRouterWDSBridgeEntry ::=
    SEQUENCE    {
                arrisRouterWDSBridgeIndex       Integer32,
                arrisRouterWDSBridgeAddr	MacAddress,
                arrisRouterWDSBridgeStatus      RowStatus
    }

arrisRouterWDSBridgeIndex OBJECT-TYPE
    SYNTAX      Integer32 (1..4)
    MAX-ACCESS  not-accessible
    STATUS      current
    DESCRIPTION
        "Indicates the instance of this table row."
    ::= { arrisRouterWDSBridgeEntry 1 }

arrisRouterWDSBridgeAddr OBJECT-TYPE
    SYNTAX      MacAddress
    MAX-ACCESS  read-create
    STATUS      current
    DESCRIPTION
        "A MAC address of a WAP which will be allowed to connect to this WAP."
    ::= { arrisRouterWDSBridgeEntry 2 }

arrisRouterWDSBridgeStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterWDSBridgeStatus column is 'notReady'.

         In particular, a newly created row cannot be made active until the
         corresponding instance of arrisRouterWDSBridgeAddr has been set.

         Only rows with a status of active(1) will be applied."
    ::= { arrisRouterWDSBridgeEntry 3 }

arrisRouterWiFiEnableRadioNow OBJECT-TYPE
     SYNTAX      TruthValue
     MAX-ACCESS  read-write
     STATUS      current
     DESCRIPTION "Enable or disable WiFi radio and immediately apply the change."
     DEFVAL { true }
     ::= { arrisRouterWirelessCfg 33 }

arrisRouterWiFiCustomSSIDStr OBJECT-TYPE
     SYNTAX      DisplayString
     MAX-ACCESS  read-write
     STATUS      current
     DESCRIPTION "A string used to customize the Service Set Idenitifer (SSID). The last 4 characters of the CM MAC address will automatically be appended to this string.
                  This string will overwrite the factory defined SSID but will be overwritten by user settings."
     ::= { arrisRouterWirelessCfg 34 }

arrisRouterWiFiReset OBJECT-TYPE
     SYNTAX      TruthValue
     MAX-ACCESS  read-write
     STATUS      current
     DESCRIPTION "Set to true to reset (restart) only the Wifi driver."
     ::= { arrisRouterWirelessCfg 35 }

arrisRouterWiFiUseSNForPSK OBJECT-TYPE
     SYNTAX      TruthValue
     MAX-ACCESS  read-write
     STATUS      current
     DESCRIPTION "Set to true to use the device serial number as the default WPA Pre-Shared Key."
     DEFVAL { false }
     ::= { arrisRouterWirelessCfg 36 }

arrisRouterWiFiRadioControlMode OBJECT-TYPE
     SYNTAX      INTEGER { userControlled(0), msoControlled24bgnMode(1), msoControlled24nMode(2), msoControlled50nMode(3) }
     MAX-ACCESS  read-write
     STATUS      current
     DESCRIPTION "When equal to userControlled, no wireless radio settings will be changed as a result of receiving this element.
                  Current setting will remain in effect.

                  When equal to msoControlled24bgnMode, the current channel numbers and channel bandwidth selections will remain
                  in effect. For devices with a single wireless network interface, all other wireless radio settings will be set so
                  as to optimize support for a mixture of 802.11b/g/n devices using the 2.4GHz band.  For devices with two wireless
                  network interfaces, all other wireless radio settings for one radio will be set so as to optimize support for a
                  mixture of 802.11b/g/n devices using the 2.4GHz band, while settings for the other radio will be set so as to
                  optimize support for only 802.11n devices using the 5GHz band. All radios MUST be set to transmit at full power.

                  When equal to msoControlled24nMode, the current channel numbers and channel bandwidth selections will remain in
                  effect. For devices with a single wireless network interface, all other wireless radio settings will be set so as
                  to optimize support for only 802.11n devices using the 2.4GHz band.  For devices with two wireless network interfaces,
                  all other wireless radio settings for one radio will be set so as to optimize support for only 802.11n devices using
                  the 2.4GHz band, while settings for the other radio will be set so as to optimize support for only 802.11n devices
                  using the 5GHz band. All radios MUST be set to transmit at full power.

                  When equal to msoControlled50nMode, the current channel numbers and channel bandwidth selections will remain in
                  effect. For devices with a single wireless network interface, all other wireless radio settings will be set so as
                  to optimize support for only 802.11n devices using the 5GHz band.  If the single wireless network interface does not
                  support use of the 5GHz band, optimize support for only 802.11n devices using the 2.4GHz band. For devices with two
                  wireless network interfaces, all other wireless radio settings for one radio will be set so as to optimize support
                  for only 802.11n devices using the 2.4GHz band, while settings for the other radio will be set so as to optimize support
                  for only 802.11n devices using the 5GHz band. All radios MUST be set to transmit at full power."
     DEFVAL {userControlled}
     ::= { arrisRouterWirelessCfg 37 }

arrisRouterWiFiAutoChannelTime OBJECT-TYPE
     SYNTAX      Integer32 (0..180)
     UNITS       "minutes"
     MAX-ACCESS  read-write
     STATUS      current
     DESCRIPTION "The WiFi module will check for channel interference and, if needed, change the WiFi channel at the interval defined here.  Set to zero to disable channel auto-scan.
                    This value will be zero if arrisRouterWiFiChannel is NOT set to auto (0)."
     DEFVAL { 10 }
     ::= { arrisRouterWirelessCfg 38 }

arrisRouterWiFiScan			 OBJECT IDENTIFIER ::= { arrisRouterWirelessCfg 39 }

arrisRouterWiFiStartScan OBJECT-TYPE
     SYNTAX      INTEGER { startRadio0(1), startRadio1(2) }
     MAX-ACCESS  read-write
     STATUS      current
     DESCRIPTION "Start a WiFi scan.  This will detect other WiFi Access Points in the vicinity of the Arris product.
                    This is useful for technical support personnel so they may detect possible wireless interference when a customer calls about their wireless.
                    Note that this may impact wireless/eRouter performance and should be run with care.
                    Note that this is currently only supported on the Arris Whole Home Solution product line."
     DEFVAL { startRadio0 }
     ::= { arrisRouterWiFiScan 1 }

arrisRouterWiFiScanResult OBJECT-TYPE
     SYNTAX      INTEGER { uninit(0), running(1), completeError(2), completeSuccess(3) }
     MAX-ACCESS  read-only
     STATUS      current
     DESCRIPTION "Returns the current status of a WiFi scan."
     ::= { arrisRouterWiFiScan 2 }

arrisRouterWiFiScanResultTable  OBJECT-TYPE
    SYNTAX      SEQUENCE OF ArrisRouterWiFiScanResultEntry
    MAX-ACCESS  not-accessible
    STATUS      current
    DESCRIPTION  "A table of any WiFi Access points in the vicinity of the Arris product."
    ::= { arrisRouterWiFiScan 3 }

arrisRouterWiFiScanResultEntry OBJECT-TYPE
    SYNTAX      ArrisRouterWiFiScanResultEntry
    MAX-ACCESS  not-accessible
    STATUS      current
    DESCRIPTION  "A table of any WiFi Access points in the vicinity of the Arris product."
    INDEX   { arrisRouterWiFiScanIndex }
    ::= { arrisRouterWiFiScanResultTable  1 }

ArrisRouterWiFiScanResultEntry ::=
    SEQUENCE    {
                arrisRouterWiFiScanIndex            Unsigned32,
                arrisRouterWiFiScanSSID             DisplayString,
                arrisRouterWiFiScanChannel          Unsigned32,
                arrisRouterWiFiScanChannel2         Unsigned32,
                arrisRouterWiFiScanRSSI             Integer32,
                arrisRouterWiFiScanNoise            Integer32,
                arrisRouterWiFiScanMAC              DisplayString,
                arrisRouterWiFiScanMfg              DisplayString,
                arrisRouterWiFiScanSupportedRates   DisplayString,
		arrisRouterWiFiScanOperatingStandards         DisplayString,
		arrisRouterWiFiScanSecurityModeEnabled        INTEGER,
		arrisRouterWiFiScanOperatingChannelBandwidth  INTEGER
                }

arrisRouterWiFiScanIndex OBJECT-TYPE
    SYNTAX      Unsigned32
    MAX-ACCESS  not-accessible
    STATUS      current
    DESCRIPTION  "Indicates the instance of this table row."
    ::= { arrisRouterWiFiScanResultEntry 1 }

arrisRouterWiFiScanSSID OBJECT-TYPE
    SYNTAX      DisplayString
    MAX-ACCESS  read-only
    STATUS      current
    DESCRIPTION  "The SSID for the wireless access point (WAP)"
    ::= { arrisRouterWiFiScanResultEntry 2 }

arrisRouterWiFiScanChannel OBJECT-TYPE
    SYNTAX      Unsigned32
    MAX-ACCESS  read-only
    STATUS      current
    DESCRIPTION  "The channel that the WAP is broadcasting on."
    ::= { arrisRouterWiFiScanResultEntry 3 }

arrisRouterWiFiScanChannel2 OBJECT-TYPE
    SYNTAX      Unsigned32
    MAX-ACCESS  read-only
    STATUS      current
    DESCRIPTION  "The secondary channel that the WAP is broadcasting on.  This may be 0 if the AP is only using 1 channel."
    ::= { arrisRouterWiFiScanResultEntry 4 }

arrisRouterWiFiScanRSSI OBJECT-TYPE
    SYNTAX      Integer32
    UNITS       "dBm"
    MAX-ACCESS  read-only
    STATUS      current
    DESCRIPTION  "The Received Signal Strength Indication (RSSI) for the WAP."
    ::= { arrisRouterWiFiScanResultEntry 5 }

arrisRouterWiFiScanNoise OBJECT-TYPE
    SYNTAX      Integer32
    UNITS       "dBm"
    MAX-ACCESS  read-only
    STATUS      current
    DESCRIPTION  "The 'noise' meausured for the WAP."
    ::= { arrisRouterWiFiScanResultEntry 6 }

arrisRouterWiFiScanMAC OBJECT-TYPE
    SYNTAX      DisplayString
    MAX-ACCESS  read-only
    STATUS      current
    DESCRIPTION  "The MAC identifier (AKA BSSID) of the WAP."
    ::= { arrisRouterWiFiScanResultEntry 7 }

arrisRouterWiFiScanMfg OBJECT-TYPE
    SYNTAX      DisplayString
    MAX-ACCESS  read-only
    STATUS      current
    DESCRIPTION  "The manufacturuer of the detected WAP."
    ::= { arrisRouterWiFiScanResultEntry 8 }

arrisRouterWiFiScanSupportedRates OBJECT-TYPE
    SYNTAX      DisplayString
    MAX-ACCESS  read-only
    STATUS      current
    DESCRIPTION  "The supported rates of the WAP.
                   i.e.  1(b) 2(b) 5.5(b) 6 9 11(b) 12 18 24 36 48 54"
    ::= { arrisRouterWiFiScanResultEntry 9 }

arrisRouterWiFiScanOperatingStandards OBJECT-TYPE
    SYNTAX      DisplayString
    MAX-ACCESS  read-only
    STATUS      current
    DESCRIPTION  "The operating standards of the WAP."
    ::= { arrisRouterWiFiScanResultEntry 10 }

arrisRouterWiFiScanSecurityModeEnabled OBJECT-TYPE
    SYNTAX      INTEGER {
                unknow(0),
                disabled(1),
                wep(2),
                wpa(3),
                wpa2(4),
                wpaWpa2(5),
                wpaEnterprise(6),
                wpa2Enterprise(7),
                wpaWpa2Enterprise(8)
    }
    MAX-ACCESS  read-only
    STATUS      current
    DESCRIPTION  "The security mode of the WAP."
    ::= { arrisRouterWiFiScanResultEntry 11 }

arrisRouterWiFiScanOperatingChannelBandwidth OBJECT-TYPE
    SYNTAX      INTEGER {
                auto(0),
                n20Mhz(1),
                n40Mhz(2),
                ac80Mhz(3),
                ac160Mhz(4)
    }
    MAX-ACCESS  read-only
    STATUS      current
    DESCRIPTION "The operating channel bandwidth of the WAP."
    ::= { arrisRouterWiFiScanResultEntry 12 }

arrisRouterWiFiUtilityCommand OBJECT-TYPE
    SYNTAX      DisplayString
    MAX-ACCESS  read-write
    STATUS      current
    DESCRIPTION  "A command to send to the wireless utility."
    ::= { arrisRouterWirelessCfg 40 }

arrisRouterWiFiUtilityCommandOutput OBJECT-TYPE
    SYNTAX      DisplayString
    MAX-ACCESS  read-only
    STATUS      current
    DESCRIPTION  "The output of the from the wireless utility after executing arrisRouterWiFiUtilityCommand."
    ::= { arrisRouterWirelessCfg 41 }

-- Wireless client info table

arrisRouterWiFiClientInfoTable OBJECT-TYPE
      SYNTAX      SEQUENCE OF ArrisRouterWiFiClientInfoClientEntry
      MAX-ACCESS  not-accessible
      STATUS      current
      DESCRIPTION "This table contains detailed information about currently connected wireless client devices."
      ::= { arrisRouterWirelessCfg 42 }

arrisRouterWiFiClientInfoEntry OBJECT-TYPE
      SYNTAX      ArrisRouterWiFiClientInfoClientEntry
      MAX-ACCESS  not-accessible
      STATUS      current
      DESCRIPTION "Entry in the arrisRouterWiFiClientInfoTable."
      INDEX { ifIndex, arrisRouterWiFiClientInfoIndex }
      ::= { arrisRouterWiFiClientInfoTable 1 }

ArrisRouterWiFiClientInfoClientEntry ::= SEQUENCE {
        arrisRouterWiFiClientInfoIndex            Integer32,
        arrisRouterWiFiClientInfoIPAddrType       InetAddressType,
        arrisRouterWiFiClientInfoIPAddr           InetAddress,
        arrisRouterWiFiClientInfoIPAddrTextual    DisplayString,
        arrisRouterWiFiClientInfoHostName         DisplayString,
        arrisRouterWiFiClientInfoMAC              MacAddress,
        arrisRouterWiFiClientInfoMACMfg           DisplayString,
        arrisRouterWiFiClientInfoStatus           INTEGER,
        arrisRouterWiFiClientInfoFirstSeen        DateAndTime,
        arrisRouterWiFiClientInfoLastSeen         DateAndTime,
        arrisRouterWiFiClientInfoIdleTime         Integer32,
        arrisRouterWiFiClientInfoInNetworkTime    Integer32,
        arrisRouterWiFiClientInfoState            DisplayString,
        arrisRouterWiFiClientInfoFlags            DisplayString,
        arrisRouterWiFiClientInfoTxPkts           Integer32,
        arrisRouterWiFiClientInfoTxFailures       Integer32,
        arrisRouterWiFiClientInfoRxUnicastPkts    Integer32,
        arrisRouterWiFiClientInfoRxMulticastPkts  Integer32,
        arrisRouterWiFiClientInfoLastTxPktRate    Integer32,
        arrisRouterWiFiClientInfoLastRxPktRate    Integer32,
        arrisRouterWiFiClientInfoRateSet          DisplayString,
        arrisRouterWiFiClientInfoRSSI             Integer32,
        arrisRouterWiFiClientInfoRxDecryptOk      Integer32,
        arrisRouterWiFiClientInfoRxDecryptFail    Integer32,
        arrisRouterWiFiClientInfoDHCPStatus       DisplayString,
        arrisRouterWiFiClientInfoInterferenceSources       INTEGER,
        arrisRouterWiFiClientInfoDataFramesSentAck         INTEGER,
        arrisRouterWiFiClientInfoDataFramesSentNoAck       INTEGER,
        arrisRouterWiFiClientInfoBytesSent                 INTEGER,
        arrisRouterWiFiClientInfoBytesReceived             INTEGER,
        arrisRouterWiFiClientInfoMinRSSI                   INTEGER,
        arrisRouterWiFiClientInfoMaxRSSI                   INTEGER,
        arrisRouterWiFiClientInfoDisassociations           DisplayString,
        arrisRouterWiFiClientInfoAuthenticationFailures    INTEGER,
        arrisRouterWiFiClientInfoOperatingStandard         DisplayString,
        arrisRouterWiFiClientInfoOperatingChannelBandwidth INTEGER,
        arrisRouterWiFiClientInfoSNR                       INTEGER,
        arrisRouterWiFiClientInfoVlanId                    Unsigned32
        }

arrisRouterWiFiClientInfoIndex OBJECT-TYPE
     SYNTAX      Integer32 (1..64)
     MAX-ACCESS  not-accessible
     STATUS      current
     DESCRIPTION "Index for the table.
                  NOTE: For TS7.x, this mib only supports (1..32)."
     ::= { arrisRouterWiFiClientInfoEntry 1 }

arrisRouterWiFiClientInfoIPAddrType OBJECT-TYPE
     SYNTAX      InetAddressType
     MAX-ACCESS  read-only
     STATUS      current
     DESCRIPTION "Current IP address type for the wireless client device."
     ::= { arrisRouterWiFiClientInfoEntry 2 }

arrisRouterWiFiClientInfoIPAddr OBJECT-TYPE
     SYNTAX      InetAddress
     MAX-ACCESS  read-only
     STATUS      current
     DESCRIPTION "Current IP address for the wireless client device."
     ::= { arrisRouterWiFiClientInfoEntry 3 }

arrisRouterWiFiClientInfoIPAddrTextual OBJECT-TYPE
     SYNTAX      DisplayString
     MAX-ACCESS  read-only
     STATUS      current
     DESCRIPTION "A human-readable textual representation of the arrisRouterWiFiClientInfoIPAddr."
     ::= { arrisRouterWiFiClientInfoEntry 4 }

arrisRouterWiFiClientInfoHostName OBJECT-TYPE
     SYNTAX      DisplayString (SIZE (0..64))
     MAX-ACCESS  read-only
     STATUS      current
     DESCRIPTION "Hostname for the wireless client device."
     ::= { arrisRouterWiFiClientInfoEntry 5 }

arrisRouterWiFiClientInfoMAC OBJECT-TYPE
     SYNTAX      MacAddress
     MAX-ACCESS  read-only
     STATUS      current
     DESCRIPTION "MAC address of the wireless client device."
     ::= { arrisRouterWiFiClientInfoEntry 6 }

arrisRouterWiFiClientInfoMACMfg OBJECT-TYPE
     SYNTAX DisplayString (SIZE(0..64))
     MAX-ACCESS read-only
     STATUS current
     DESCRIPTION "The manufacturer of the hardware adapter on the wireless client device."
     ::= { arrisRouterWiFiClientInfoEntry 7 }

arrisRouterWiFiClientInfoStatus OBJECT-TYPE
     SYNTAX      INTEGER { down(0), up(1) }
     MAX-ACCESS read-only
     STATUS current
     DESCRIPTION "The most recent known status of the wireless client device."
     ::= { arrisRouterWiFiClientInfoEntry 8 }

arrisRouterWiFiClientInfoFirstSeen OBJECT-TYPE
     SYNTAX      DateAndTime
     MAX-ACCESS read-only
     STATUS current
     DESCRIPTION "The time, if known, when this client was first seen.
                For 'dynamic' clients, this will usually be when the first DHCP lease was given out to this client since the last boot.
                For 'staticDiscover' clients, this value will match the time of the first ARP response since the last boot.
                For 'staticConfigure' clients, this value will match the time of the first ARP response since the last boot."
     ::= { arrisRouterWiFiClientInfoEntry 9 }

arrisRouterWiFiClientInfoLastSeen OBJECT-TYPE
     SYNTAX      DateAndTime
     MAX-ACCESS read-only
     STATUS current
     DESCRIPTION "The time, if known, when this client was most recently (last) seen.
                  If the device has been disconnected or powered off this value will reflect that.
                  If the device is currently active, this value should match the current system time with a variability of up to 1 minute."
     ::= { arrisRouterWiFiClientInfoEntry 10 }

arrisRouterWiFiClientInfoIdleTime OBJECT-TYPE
     SYNTAX     Integer32
     UNITS      "seconds"
     MAX-ACCESS read-only
     STATUS current
     DESCRIPTION "The number of seconds that this wireless client device has been idle."
     ::= { arrisRouterWiFiClientInfoEntry 11 }

arrisRouterWiFiClientInfoInNetworkTime OBJECT-TYPE
     SYNTAX     Integer32
     UNITS      "seconds"
     MAX-ACCESS read-only
     STATUS current
     DESCRIPTION "The number of seconds that this wireless client device has been in the network.
                  This value will be reset when the wireless client device is disconnected or powered off.
                  Thus this may not be equal to the elapsed time since: arrisRouterWiFiClientInfoFirstSeen."
     ::= { arrisRouterWiFiClientInfoEntry 12 }

arrisRouterWiFiClientInfoState OBJECT-TYPE
     SYNTAX     DisplayString
     MAX-ACCESS read-only
     STATUS current
     DESCRIPTION "A string representing the current connection state of this wireless client device.
                  It will indicate if the device is: AUTHENTICATED, ASSOCIATED, and/or AUTHORIZED."
     ::= { arrisRouterWiFiClientInfoEntry 13 }

arrisRouterWiFiClientInfoFlags OBJECT-TYPE
     SYNTAX     DisplayString
     MAX-ACCESS read-only
     STATUS current
     DESCRIPTION "A string representing the current various capability flags for this wireless client device."
     ::= { arrisRouterWiFiClientInfoEntry 14 }

arrisRouterWiFiClientInfoTxPkts OBJECT-TYPE
     SYNTAX     Integer32
     UNITS      "packets"
     MAX-ACCESS read-only
     STATUS current
     DESCRIPTION "The number packets transmitted from this wireless client device since it was last connected."
     ::= { arrisRouterWiFiClientInfoEntry 15 }

arrisRouterWiFiClientInfoTxFailures OBJECT-TYPE
     SYNTAX     Integer32
     UNITS      "packets"
     MAX-ACCESS read-only
     STATUS current
     DESCRIPTION "The number transmit packet failures from this wireless client device since it was last connected."
     ::= { arrisRouterWiFiClientInfoEntry 16 }

arrisRouterWiFiClientInfoRxUnicastPkts OBJECT-TYPE
     SYNTAX     Integer32
     UNITS      "packets"
     MAX-ACCESS read-only
     STATUS current
     DESCRIPTION "The number of unicast packets received by this wireless client device since it was last connected."
     ::= { arrisRouterWiFiClientInfoEntry 17 }

arrisRouterWiFiClientInfoRxMulticastPkts OBJECT-TYPE
     SYNTAX     Integer32
     UNITS      "packets"
     MAX-ACCESS read-only
     STATUS current
     DESCRIPTION "The number of multicast/broadcast packets received by this wireless client device since it was last connected."
     ::= { arrisRouterWiFiClientInfoEntry 18 }

arrisRouterWiFiClientInfoLastTxPktRate OBJECT-TYPE
     SYNTAX     Integer32
     UNITS      "kbps"
     MAX-ACCESS read-only
     STATUS current
     DESCRIPTION "The transmission rate of the last packet transmitted from this wireless client device in kilobits-per-second."
     ::= { arrisRouterWiFiClientInfoEntry 19 }

arrisRouterWiFiClientInfoLastRxPktRate OBJECT-TYPE
     SYNTAX     Integer32
     UNITS      "kbps"
     MAX-ACCESS read-only
     STATUS current
     DESCRIPTION "The reception rate of the last packet received by this wireless client device in kilobits-per-second."
     ::= { arrisRouterWiFiClientInfoEntry 20 }

arrisRouterWiFiClientInfoRateSet OBJECT-TYPE
     SYNTAX     DisplayString
     MAX-ACCESS read-only
     STATUS current
     DESCRIPTION "The supported rate set for this wireless client device."
     ::= { arrisRouterWiFiClientInfoEntry 21 }

arrisRouterWiFiClientInfoRSSI OBJECT-TYPE
     SYNTAX     Integer32
     MAX-ACCESS read-only
     STATUS current
     DESCRIPTION "The Received Signal Strength Indicator (RSSI) of the wireless client device.
                  This value usually displays as a negative, so a value closer to zero indicates more power."
     ::= { arrisRouterWiFiClientInfoEntry 22 }

arrisRouterWiFiClientInfoRxDecryptOk OBJECT-TYPE
     SYNTAX     Integer32
     MAX-ACCESS read-only
     STATUS current
     DESCRIPTION "The number of receive packets successfully decrypted"
     ::= { arrisRouterWiFiClientInfoEntry 23 }

arrisRouterWiFiClientInfoRxDecryptFail OBJECT-TYPE
     SYNTAX     Integer32
     MAX-ACCESS read-only
     STATUS current
     DESCRIPTION "The number of receive packets that failed to be decrypted"
     ::= { arrisRouterWiFiClientInfoEntry 24 }

arrisRouterWiFiClientInfoDHCPStatus OBJECT-TYPE
     SYNTAX     DisplayString
     MAX-ACCESS read-only
     STATUS current
     DESCRIPTION "A string representing the current DHCP status of this wireless client device after it has associated.
     It will indicate if the device is: DISCOVERED, REQUESTED, CONNECTED or FAILED.
     DISCOVERED: device has sent out DHCP Discover packet,
     REQUESTED: device has sent out DHCP Request packet,
     CONNECTED: DHCP has finished successfully,
     FAILED: device can't get an IP, DHCP is failed."
     ::= { arrisRouterWiFiClientInfoEntry 25 }

arrisRouterWiFiClientInfoInterferenceSources  OBJECT-TYPE
     SYNTAX      INTEGER
     MAX-ACCESS  read-only
     STATUS      current
     DESCRIPTION "Clients Interference Sources"
     ::= { arrisRouterWiFiClientInfoEntry 26 }

arrisRouterWiFiClientInfoDataFramesSentAck  OBJECT-TYPE
     SYNTAX      INTEGER
     MAX-ACCESS  read-only
     STATUS      current
     DESCRIPTION "Clients Data Frames Sent Ack"
     ::= { arrisRouterWiFiClientInfoEntry 27 }

arrisRouterWiFiClientInfoDataFramesSentNoAck  OBJECT-TYPE
     SYNTAX      INTEGER
     MAX-ACCESS  read-only
     STATUS      current
     DESCRIPTION "Clients Data Frames Sent No Ack"
     ::= { arrisRouterWiFiClientInfoEntry 28 }

arrisRouterWiFiClientInfoBytesSent   OBJECT-TYPE
     SYNTAX      INTEGER
     MAX-ACCESS  read-only
     STATUS      current
     DESCRIPTION "Clients Bytes Sent"
     ::= { arrisRouterWiFiClientInfoEntry 29 }

arrisRouterWiFiClientInfoBytesReceived  OBJECT-TYPE
     SYNTAX      INTEGER
     MAX-ACCESS  read-only
     STATUS      current
     DESCRIPTION "Clients Bytes Received"
     ::= { arrisRouterWiFiClientInfoEntry 30 }

arrisRouterWiFiClientInfoMinRSSI OBJECT-TYPE
     SYNTAX      INTEGER
     MAX-ACCESS  read-only
     STATUS      current
     DESCRIPTION "Clients Minimum RSSI"
     ::= { arrisRouterWiFiClientInfoEntry 31 }

arrisRouterWiFiClientInfoMaxRSSI OBJECT-TYPE
     SYNTAX      INTEGER
     MAX-ACCESS  read-only
     STATUS      current
     DESCRIPTION "Clients Max RSSI"
     ::= { arrisRouterWiFiClientInfoEntry 32 }

arrisRouterWiFiClientInfoDisassociations OBJECT-TYPE
     SYNTAX      DisplayString
     MAX-ACCESS  read-only
     STATUS      current
     DESCRIPTION "Clients Disassociations"
     ::= { arrisRouterWiFiClientInfoEntry 33 }

arrisRouterWiFiClientInfoAuthenticationFailures OBJECT-TYPE
     SYNTAX      INTEGER
     MAX-ACCESS  read-only
     STATUS      current
     DESCRIPTION "Clients Authentication  Failures"
     ::= { arrisRouterWiFiClientInfoEntry 34 }

arrisRouterWiFiClientInfoOperatingStandard OBJECT-TYPE
     SYNTAX      DisplayString
     MAX-ACCESS  read-only
     STATUS      current
     DESCRIPTION "Clients Operating Standard"
     ::= { arrisRouterWiFiClientInfoEntry 35 }

arrisRouterWiFiClientInfoOperatingChannelBandwidth OBJECT-TYPE
     SYNTAX      INTEGER
     MAX-ACCESS  read-only
     STATUS      current
     DESCRIPTION "Clients Operating Channel Bandwidth"
     ::= { arrisRouterWiFiClientInfoEntry 36 }

arrisRouterWiFiClientInfoSNR  OBJECT-TYPE
     SYNTAX      INTEGER
     MAX-ACCESS  read-only
     STATUS      current
     DESCRIPTION "Clients SNR"
     ::= { arrisRouterWiFiClientInfoEntry 37 }

arrisRouterWiFiClientInfoVlanId  OBJECT-TYPE
     SYNTAX      Unsigned32
     MAX-ACCESS  read-only
     STATUS      current
     DESCRIPTION "Clients Vlan ID."
     ::= { arrisRouterWiFiClientInfoEntry 38 }

arrisRouterWiFiPhysicalChannel OBJECT-TYPE
      SYNTAX      Integer32
      MAX-ACCESS  read-only
      STATUS      current
      DESCRIPTION  "The current channel the WiFi is using.
                    This may match arrisRouterWiFiChannel except when that value is auto(0).
                    When the 'auto' mode is used, this OID will return the actual channel being used."
      ::= { arrisRouterWirelessCfg 43 }

arrisRouterWiFiTxPowerPhysical OBJECT-TYPE
    SYNTAX      Integer32
    UNITS       "qdbm"
    MAX-ACCESS  read-only
    STATUS      current
    DESCRIPTION  "The current measured transmit power of the wireless access point (WAP).  Divide by 4 to convert to dbm."
    ::= { arrisRouterWirelessCfg 44 }

arrisRouterWiFiShortSlotEnhanced OBJECT-TYPE
     SYNTAX      INTEGER { auto(-1), long(0), short(1) }
     MAX-ACCESS  read-write
     STATUS      current
     DESCRIPTION "An enhanced enable short slot timing mode.  An option to use 'auto' is new.
                    The amount of time a device waits after a collision before retransmitting a packet.
                    You can increase throughput on 802.11g, 2.4-GHz radios by enabling short slot time."
     DEFVAL { auto }
     ::= { arrisRouterWirelessCfg 45 }

arrisRouterAdvanceWirelessStats			 OBJECT IDENTIFIER ::= { arrisRouterWirelessCfg 46 }

arrisRouterAdvanceWirelessStatsXmit 	 OBJECT IDENTIFIER ::= { arrisRouterAdvanceWirelessStats 1 }
arrisRouterAdvanceWirelessStatsRecv 	 OBJECT IDENTIFIER ::= { arrisRouterAdvanceWirelessStats 2 }
arrisRouterAdvanceWirelessStatsEncrypt 	 OBJECT IDENTIFIER ::= { arrisRouterAdvanceWirelessStats 3 }
arrisRouterAdvanceWirelessStatsRateStats OBJECT IDENTIFIER ::= { arrisRouterAdvanceWirelessStats 4 }


arrisRouterTxFrameCount OBJECT-TYPE
    SYNTAX      Integer32
    MAX-ACCESS  read-only
    STATUS      current
    DESCRIPTION  "Current count of transmit data frames."
    ::= { arrisRouterAdvanceWirelessStatsXmit 1 }

arrisRouterTxBytesCount OBJECT-TYPE
    SYNTAX      Integer32
    MAX-ACCESS  read-only
    STATUS      current
    DESCRIPTION  "Current count of transmit data bytes."
    ::= { arrisRouterAdvanceWirelessStatsXmit 2 }

arrisRouterTxRetransmitCount OBJECT-TYPE
    SYNTAX      Integer32
    MAX-ACCESS  read-only
    STATUS      current
    DESCRIPTION  "Current count of MAC retransmits."
    ::= { arrisRouterAdvanceWirelessStatsXmit 3 }

arrisRouterTxErrorCount OBJECT-TYPE
    SYNTAX      Integer32
    MAX-ACCESS  read-only
    STATUS      current
    DESCRIPTION  "Current count of transmit data errors."
    ::= { arrisRouterAdvanceWirelessStatsXmit 4 }

arrisRouterTxMgmtFrames OBJECT-TYPE
    SYNTAX      Integer32
    MAX-ACCESS  read-only
    STATUS      current
    DESCRIPTION  "Current count of transmit management frames."
    ::= { arrisRouterAdvanceWirelessStatsXmit 5 }

arrisRouterTxShortPreambleFrames OBJECT-TYPE
    SYNTAX      Integer32
    MAX-ACCESS  read-only
    STATUS      current
    DESCRIPTION  "Current count of transmit short preamble frames."
    ::= { arrisRouterAdvanceWirelessStatsXmit 6 }

arrisRouterTxStatusErrors OBJECT-TYPE
    SYNTAX      Integer32
    MAX-ACCESS  read-only
    STATUS      current
    DESCRIPTION  "Current count of transmit status errors."
    ::= { arrisRouterAdvanceWirelessStatsXmit 7 }

arrisRouterTxOutOfBufsErrors OBJECT-TYPE
    SYNTAX      Integer32
    MAX-ACCESS  read-only
    STATUS      current
    DESCRIPTION  "Current count of transmit out of buffers errors."
    ::= { arrisRouterAdvanceWirelessStatsXmit 8 }

arrisRouterTxNoAssocErrors OBJECT-TYPE
    SYNTAX      Integer32
    MAX-ACCESS  read-only
    STATUS      current
    DESCRIPTION  "Current count of transmit errors caused because of no wireless association."
    ::= { arrisRouterAdvanceWirelessStatsXmit 9 }

arrisRouterTxRuntCount OBJECT-TYPE
    SYNTAX      Integer32
    MAX-ACCESS  read-only
    STATUS      current
    DESCRIPTION  "Current count of transmit runt frames. Any frame which is received and which is less than 64 bytes (18 bytes Header/CRC and 46 bytes data) is illegal, and is called a 'runt'.
                   In most cases, such frames arise from a collision, and while they indicate an illegal reception, they may be observed on correctly functioning networks."
    ::= { arrisRouterAdvanceWirelessStatsXmit 10 }

arrisRouterTxHeaderCacheHit OBJECT-TYPE
    SYNTAX      Integer32
    MAX-ACCESS  read-only
    STATUS      current
    DESCRIPTION  "Current count of transmit header cache hit."
    ::= { arrisRouterAdvanceWirelessStatsXmit 11 }

arrisRouterTxHeaderCacheMiss OBJECT-TYPE
    SYNTAX      Integer32
    MAX-ACCESS  read-only
    STATUS      current
    DESCRIPTION  "Current count of transmit header cache miss."
    ::= { arrisRouterAdvanceWirelessStatsXmit 12 }

arrisRouterTxFIFOUnderflows OBJECT-TYPE
    SYNTAX      Integer32
    MAX-ACCESS  read-only
    STATUS      current
    DESCRIPTION  "Current count of transmit FIFO underflows."
    ::= { arrisRouterAdvanceWirelessStatsXmit 13 }

arrisRouterTxPhyErrors OBJECT-TYPE
    SYNTAX      Integer32
    MAX-ACCESS  read-only
    STATUS      current
    DESCRIPTION  "Current count of transmit physical layer errors."
    ::= { arrisRouterAdvanceWirelessStatsXmit 14 }

arrisRouterTxPhyCRS OBJECT-TYPE
    SYNTAX      Integer32
    MAX-ACCESS  read-only
    STATUS      current
    DESCRIPTION  "Current count of transmit physical layer CRS.."
    ::= { arrisRouterAdvanceWirelessStatsXmit 15 }

arrisRouterTxAllFrameCount OBJECT-TYPE
    SYNTAX      Integer32
    MAX-ACCESS  read-only
    STATUS      current
    DESCRIPTION  "Total number of frames sent, incl. Data, ACK, RTS, CTS, Control Management (includes retransmissions)."
    ::= { arrisRouterAdvanceWirelessStatsXmit 16 }

arrisRouterTxDMAWarCount OBJECT-TYPE
    SYNTAX      Integer32
    MAX-ACCESS  read-only
    STATUS      current
    DESCRIPTION  "Total number of transmit DMA 'war' todo."
    ::= { arrisRouterAdvanceWirelessStatsXmit 17 }

arrisRouterTxRTSFrameCount OBJECT-TYPE
    SYNTAX      Integer32
    MAX-ACCESS  read-only
    STATUS      current
    DESCRIPTION  "Current count of RTS transmit frames."
    ::= { arrisRouterAdvanceWirelessStatsXmit 18 }

arrisRouterTxCTSFrameCount OBJECT-TYPE
    SYNTAX      Integer32
    MAX-ACCESS  read-only
    STATUS      current
    DESCRIPTION  "Current count of CTS transmit frames."
    ::= { arrisRouterAdvanceWirelessStatsXmit 19 }

arrisRouterTxAckFrameCount OBJECT-TYPE
    SYNTAX      Integer32
    MAX-ACCESS  read-only
    STATUS      current
    DESCRIPTION  "Current count of ACK transmit frames."
    ::= { arrisRouterAdvanceWirelessStatsXmit 20 }

arrisRouterTxDNLFrameCount OBJECT-TYPE
    SYNTAX      Integer32
    MAX-ACCESS  read-only
    STATUS      current
    DESCRIPTION  "Current count of DNL? transmit frames."
    ::= { arrisRouterAdvanceWirelessStatsXmit 21 }

arrisRouterTxBeaconFrameCount OBJECT-TYPE
    SYNTAX      Integer32
    MAX-ACCESS  read-only
    STATUS      current
    DESCRIPTION  "Current count of beacons transmitted."
    ::= { arrisRouterAdvanceWirelessStatsXmit 22 }

arrisRouterTxUnderflowCount OBJECT-TYPE
    SYNTAX      DisplayString
    MAX-ACCESS  read-only
    STATUS      current
    DESCRIPTION  "Current count of transmit underflows per FIFO.  Format is %D; %D; %D; %D; %D; %D; %D; %D; %D; "
    ::= { arrisRouterAdvanceWirelessStatsXmit 23 }

arrisRouterTxTemplateUnderflowCount OBJECT-TYPE
    SYNTAX      Integer32
    MAX-ACCESS  read-only
    STATUS      current
    DESCRIPTION  "Current count of transmit template underflows."
    ::= { arrisRouterAdvanceWirelessStatsXmit 24 }

arrisRouterTxBeaconsCanceledCount OBJECT-TYPE
    SYNTAX      Integer32
    MAX-ACCESS  read-only
    STATUS      current
    DESCRIPTION  "Current count of number of transmit beacons canceled due to receipt of beacon (IBSS)"
    ::= { arrisRouterAdvanceWirelessStatsXmit 25 }

arrisRouterTxFIFOOverflows OBJECT-TYPE
    SYNTAX      Integer32
    MAX-ACCESS  read-only
    STATUS      current
    DESCRIPTION  "Current count of number of transmit status FIFO overflows."
    ::= { arrisRouterAdvanceWirelessStatsXmit 26 }

arrisRouterTxPRFailures OBJECT-TYPE
    SYNTAX      Integer32
    MAX-ACCESS  read-only
    STATUS      current
    DESCRIPTION  "Current count of number of transmit Probe Response failures where the AP sent a probe response but did not get an ACK."
    ::= { arrisRouterAdvanceWirelessStatsXmit 27 }

arrisRouterTxPRSuccess OBJECT-TYPE
    SYNTAX      Integer32
    MAX-ACCESS  read-only
    STATUS      current
    DESCRIPTION  "Current count of number of transmit Probe Response successes where the AP sent a probe response and received an ACK."
    ::= { arrisRouterAdvanceWirelessStatsXmit 28 }

arrisRouterTxAfterburnerNACKCount OBJECT-TYPE
    SYNTAX      Integer32
    MAX-ACCESS  read-only
    STATUS      current
    DESCRIPTION  "Number of NACK 'Afterburner' frames transmitted."
    ::= { arrisRouterAdvanceWirelessStatsXmit 29 }

arrisRouterTxFragmentCount OBJECT-TYPE
    SYNTAX      Integer32
    MAX-ACCESS  read-only
    STATUS      current
    DESCRIPTION  "Transmitted fragment count."
    ::= { arrisRouterAdvanceWirelessStatsXmit 30 }

arrisRouterTxMulticastCount OBJECT-TYPE
    SYNTAX      Integer32
    MAX-ACCESS  read-only
    STATUS      current
    DESCRIPTION  "Multicast transmitted frame count."
    ::= { arrisRouterAdvanceWirelessStatsXmit 31 }

arrisRouterTxFailureCount OBJECT-TYPE
    SYNTAX      Integer32
    MAX-ACCESS  read-only
    STATUS      current
    DESCRIPTION  "Transmit failure count."
    ::= { arrisRouterAdvanceWirelessStatsXmit 32 }

arrisRouterTxRetryCount OBJECT-TYPE
    SYNTAX      Integer32
    MAX-ACCESS  read-only
    STATUS      current
    DESCRIPTION  "Transmit retry count."
    ::= { arrisRouterAdvanceWirelessStatsXmit 33 }

arrisRouterTxMultipleRetryCount OBJECT-TYPE
    SYNTAX      Integer32
    MAX-ACCESS  read-only
    STATUS      current
    DESCRIPTION  "Transmit multiple retry count."
    ::= { arrisRouterAdvanceWirelessStatsXmit 34 }

arrisRouterTxRTSSuccessCount OBJECT-TYPE
    SYNTAX      Integer32
    MAX-ACCESS  read-only
    STATUS      current
    DESCRIPTION  "This counter shall increment when a CTS is received in response to an RTS."
    ::= { arrisRouterAdvanceWirelessStatsXmit 35 }

arrisRouterTxRTSFailCount OBJECT-TYPE
    SYNTAX      Integer32
    MAX-ACCESS  read-only
    STATUS      current
    DESCRIPTION  "This counter shall increment when a CTS is NOT received in response to an RTS."
    ::= { arrisRouterAdvanceWirelessStatsXmit 36 }

arrisRouterTxAckFailCount OBJECT-TYPE
    SYNTAX      Integer32
    MAX-ACCESS  read-only
    STATUS      current
    DESCRIPTION  "This counter shall increment when an ACK is not received when expected."
    ::= { arrisRouterAdvanceWirelessStatsXmit 37 }

arrisRouterTxFrameCountDot11 OBJECT-TYPE
    SYNTAX      Integer32
    MAX-ACCESS  read-only
    STATUS      current
    DESCRIPTION  "This counter shall increment for each successfully transmitted MSDU."
    ::= { arrisRouterAdvanceWirelessStatsXmit 38 }

arrisRouterTxChannelRejectFrameCount OBJECT-TYPE
    SYNTAX      Integer32
    MAX-ACCESS  read-only
    STATUS      current
    DESCRIPTION  "This counter reports the number of transmit frames that were suppressed due to channel rejection."
    ::= { arrisRouterAdvanceWirelessStatsXmit 39 }

arrisRouterTxTimerExpirationFrameCount OBJECT-TYPE
    SYNTAX      Integer32
    MAX-ACCESS  read-only
    STATUS      current
    DESCRIPTION  "This counter reports the number of transmit frames that were suppressed due to timer expiration."
    ::= { arrisRouterAdvanceWirelessStatsXmit 40 }

arrisRouterTxGlitchNACKCount OBJECT-TYPE
    SYNTAX      Integer32
    MAX-ACCESS  read-only
    STATUS      current
    DESCRIPTION  "Count of glitch-NACK."
    ::= { arrisRouterAdvanceWirelessStatsXmit 41 }


-- Receive stats
-- arrisRouterAdvanceWirelessStatsRecv

arrisRouterRxFrame OBJECT-TYPE
    SYNTAX      Integer32
    MAX-ACCESS  read-only
    STATUS      current
    DESCRIPTION  "Current count of receive data frames."
    ::= { arrisRouterAdvanceWirelessStatsRecv 1 }

arrisRouterRxBytes OBJECT-TYPE
    SYNTAX      Integer32
    MAX-ACCESS  read-only
    STATUS      current
    DESCRIPTION  "Current count of receive data bytes."
    ::= { arrisRouterAdvanceWirelessStatsRecv 2 }

arrisRouterRxError OBJECT-TYPE
    SYNTAX      Integer32
    MAX-ACCESS  read-only
    STATUS      current
    DESCRIPTION  "Current count of receive data errors."
    ::= { arrisRouterAdvanceWirelessStatsRecv 3 }

arrisRouterRxCtl OBJECT-TYPE
    SYNTAX      Integer32
    MAX-ACCESS  read-only
    STATUS      current
    DESCRIPTION  "Current count of receive management frames."
    ::= { arrisRouterAdvanceWirelessStatsRecv 4 }

arrisRouterRxNoBufs OBJECT-TYPE
    SYNTAX      Integer32
    MAX-ACCESS  read-only
    STATUS      current
    DESCRIPTION  "Current count of receive errors due to out of buffer state."
    ::= { arrisRouterAdvanceWirelessStatsRecv 5 }

arrisRouterRxNonDataErrors OBJECT-TYPE
    SYNTAX      Integer32
    MAX-ACCESS  read-only
    STATUS      current
    DESCRIPTION  "Current count of receive non data frames in the data channel errors."
    ::= { arrisRouterAdvanceWirelessStatsRecv 6 }

arrisRouterRxBadDSErrors OBJECT-TYPE
    SYNTAX      Integer32
    MAX-ACCESS  read-only
    STATUS      current
    DESCRIPTION  "Current count of receive errors due to bad DS.  TODO desc."
    ::= { arrisRouterAdvanceWirelessStatsRecv 7 }

arrisRouterRxBadCMErrors OBJECT-TYPE
    SYNTAX      Integer32
    MAX-ACCESS  read-only
    STATUS      current
    DESCRIPTION  "Current count of receive errors due to bad control or managment frames."
    ::= { arrisRouterAdvanceWirelessStatsRecv 8 }

arrisRouterRxFragErrors OBJECT-TYPE
    SYNTAX      Integer32
    MAX-ACCESS  read-only
    STATUS      current
    DESCRIPTION  "Current count of receive errors due to fragmentation."
    ::= { arrisRouterAdvanceWirelessStatsRecv 9 }

arrisRouterRxRuntCount OBJECT-TYPE
    SYNTAX      Integer32
    MAX-ACCESS  read-only
    STATUS      current
    DESCRIPTION  "Current count of receive runt frames. Any frame which is received and which is less than 64 bytes (18 bytes Header/CRC and 46 bytes data) is illegal, and is called a 'runt'.
                   In most cases, such frames arise from a collision, and while they indicate an illegal reception, they may be observed on correctly functioning networks."
    ::= { arrisRouterAdvanceWirelessStatsRecv 10 }

arrisRouterRxGiantCount OBJECT-TYPE
    SYNTAX      Integer32
    MAX-ACCESS  read-only
    STATUS      current
    DESCRIPTION  "Current count of receive giant frames."
    ::= { arrisRouterAdvanceWirelessStatsRecv 11 }

arrisRouterRxNoSCBErrorCount OBJECT-TYPE
    SYNTAX      Integer32
    MAX-ACCESS  read-only
    STATUS      current
    DESCRIPTION  "Current count of receive errors due to no SCB."
    ::= { arrisRouterAdvanceWirelessStatsRecv 12 }

arrisRouterRxBadProtoErrorCount OBJECT-TYPE
    SYNTAX      Integer32
    MAX-ACCESS  read-only
    STATUS      current
    DESCRIPTION  "Current count of receive errors due to protocol errors, invalid frames."
    ::= { arrisRouterAdvanceWirelessStatsRecv 13 }

arrisRouterRxBadSrcMACErrorCount OBJECT-TYPE
    SYNTAX      Integer32
    MAX-ACCESS  read-only
    STATUS      current
    DESCRIPTION  "Current count of receive errors due to invalid source MAC address."
    ::= { arrisRouterAdvanceWirelessStatsRecv 14 }

arrisRouterRxBadDAErrorCount OBJECT-TYPE
    SYNTAX      Integer32
    MAX-ACCESS  read-only
    STATUS      current
    DESCRIPTION  "Current count of receive errors due to invalid DA."
    ::= { arrisRouterAdvanceWirelessStatsRecv 15 }

arrisRouterRxFilterCount OBJECT-TYPE
    SYNTAX      Integer32
    MAX-ACCESS  read-only
    STATUS      current
    DESCRIPTION  "Current count of receive frames that were filtered out."
    ::= { arrisRouterAdvanceWirelessStatsRecv 16 }

arrisRouterRxUnderflowCount OBJECT-TYPE
    SYNTAX      DisplayString
    MAX-ACCESS  read-only
    STATUS      current
    DESCRIPTION  "Current count of receive DMA descriptor underflows per FIFO.  Format is %D; %D; %D; %D; %D; %D; %D; %D; %D; "
    ::= { arrisRouterAdvanceWirelessStatsRecv 17 }

arrisRouterRxFrameTooLongCount OBJECT-TYPE
    SYNTAX      Integer32
    MAX-ACCESS  read-only
    STATUS      current
    DESCRIPTION  "Current count of receive frames that were too long (2346 bytes)"
    ::= { arrisRouterAdvanceWirelessStatsRecv 18 }

arrisRouterRxFrameTooShortCount OBJECT-TYPE
    SYNTAX      Integer32
    MAX-ACCESS  read-only
    STATUS      current
    DESCRIPTION  "Current count of receive frames that were too short."
    ::= { arrisRouterAdvanceWirelessStatsRecv 19 }

arrisRouterRxBadHeaderCount OBJECT-TYPE
    SYNTAX      Integer32
    MAX-ACCESS  read-only
    STATUS      current
    DESCRIPTION  "Current count of receive frames with protocol version not equal zero or frame type is not data, control, or management."
    ::= { arrisRouterAdvanceWirelessStatsRecv 20 }

arrisRouterRxBadFCSCount OBJECT-TYPE
    SYNTAX      Integer32
    MAX-ACCESS  read-only
    STATUS      current
    DESCRIPTION  "Current count of receive frames for which the CRC check failed in the MAC."
    ::= { arrisRouterAdvanceWirelessStatsRecv 21 }

arrisRouterRxBadPLCPCount OBJECT-TYPE
    SYNTAX      Integer32
    MAX-ACCESS  read-only
    STATUS      current
    DESCRIPTION  "Current count of receive frames for which the parity check of the PLCP header failed."
    ::= { arrisRouterAdvanceWirelessStatsRecv 22 }

arrisRouterRxRSGlitchCount OBJECT-TYPE
    SYNTAX      Integer32
    MAX-ACCESS  read-only
    STATUS      current
    DESCRIPTION  "Current count of receive frames for which the PHY was able to correlate the preamble but not the header."
    ::= { arrisRouterAdvanceWirelessStatsRecv 23 }

arrisRouterRxGoodPLCPCount OBJECT-TYPE
    SYNTAX      Integer32
    MAX-ACCESS  read-only
    STATUS      current
    DESCRIPTION  "Current count of receive frames for which the parity check of the PLCP header succeeded."
    ::= { arrisRouterAdvanceWirelessStatsRecv 24 }

arrisRouterRxDataGoodFCSCount OBJECT-TYPE
    SYNTAX      Integer32
    MAX-ACCESS  read-only
    STATUS      current
    DESCRIPTION  "Current count of number of received DATA frames with good FCS and matching RA."
    ::= { arrisRouterAdvanceWirelessStatsRecv 25 }

arrisRouterRxMgmtGoodFCSCount OBJECT-TYPE
    SYNTAX      Integer32
    MAX-ACCESS  read-only
    STATUS      current
    DESCRIPTION  "Current count of number of received management frames with good FCS and matching RA."
    ::= { arrisRouterAdvanceWirelessStatsRecv 26 }

arrisRouterRxControlGoodFCSCount OBJECT-TYPE
    SYNTAX      Integer32
    MAX-ACCESS  read-only
    STATUS      current
    DESCRIPTION  "Current count of number of received control frames with good FCS and matching RA."
    ::= { arrisRouterAdvanceWirelessStatsRecv 27 }

arrisRouterRxRTSGoodFCSCount OBJECT-TYPE
    SYNTAX      Integer32
    MAX-ACCESS  read-only
    STATUS      current
    DESCRIPTION  "Current count of number of unicast RTS addressed to the MAC (good FCS)"
    ::= { arrisRouterAdvanceWirelessStatsRecv 28 }

arrisRouterRxCTSGoodFCSCount OBJECT-TYPE
    SYNTAX      Integer32
    MAX-ACCESS  read-only
    STATUS      current
    DESCRIPTION  "Current count of number of unicast CTS addressed to the MAC (good FCS)"
    ::= { arrisRouterAdvanceWirelessStatsRecv 29 }

arrisRouterRxAcksGoodFCSCount OBJECT-TYPE
    SYNTAX      Integer32
    MAX-ACCESS  read-only
    STATUS      current
    DESCRIPTION  "Current count of number of unicast ACKS addressed to the MAC (good FCS)"
    ::= { arrisRouterAdvanceWirelessStatsRecv 30 }

arrisRouterRxDataGoodFCSNoRACount OBJECT-TYPE
    SYNTAX      Integer32
    MAX-ACCESS  read-only
    STATUS      current
    DESCRIPTION  "Current count of number of received DATA frames (good FCS and not matching RA)"
    ::= { arrisRouterAdvanceWirelessStatsRecv 31 }

arrisRouterRxMgmtGoodFCSNoRACount OBJECT-TYPE
    SYNTAX      Integer32
    MAX-ACCESS  read-only
    STATUS      current
    DESCRIPTION  "Current count of number of received MGMT frames (good FCS and not matching RA)"
    ::= { arrisRouterAdvanceWirelessStatsRecv 32 }

arrisRouterRxCTRLGoodFCSNoRACount OBJECT-TYPE
    SYNTAX      Integer32
    MAX-ACCESS  read-only
    STATUS      current
    DESCRIPTION  "Current count of number of received control frames (good FCS and not matching RA)"
    ::= { arrisRouterAdvanceWirelessStatsRecv 33 }

arrisRouterRxRTSNoMACCount OBJECT-TYPE
    SYNTAX      Integer32
    MAX-ACCESS  read-only
    STATUS      current
    DESCRIPTION  "Number of unicast RTS NOT addressed to the MAC."
    ::= { arrisRouterAdvanceWirelessStatsRecv 34 }

arrisRouterRxCTSNoMACCount OBJECT-TYPE
    SYNTAX      Integer32
    MAX-ACCESS  read-only
    STATUS      current
    DESCRIPTION  "Number of unicast CTS NOT addressed to the MAC."
    ::= { arrisRouterAdvanceWirelessStatsRecv 35 }

arrisRouterRxMulticastDataCount OBJECT-TYPE
    SYNTAX      Integer32
    MAX-ACCESS  read-only
    STATUS      current
    DESCRIPTION  "Current count of number of RX Data multicast frames received by the MAC."
    ::= { arrisRouterAdvanceWirelessStatsRecv 36 }

arrisRouterRxMulticastMgmtCount OBJECT-TYPE
    SYNTAX      Integer32
    MAX-ACCESS  read-only
    STATUS      current
    DESCRIPTION  "Current count of number of RX management multicast frames received by the MAC."
    ::= { arrisRouterAdvanceWirelessStatsRecv 37 }

arrisRouterRxMulticastCtlCount OBJECT-TYPE
    SYNTAX      Integer32
    MAX-ACCESS  read-only
    STATUS      current
    DESCRIPTION  "Current count of number of RX control multicast frames received by the MAC."
    ::= { arrisRouterAdvanceWirelessStatsRecv 38 }

arrisRouterRxMemberBeaconCount OBJECT-TYPE
    SYNTAX      Integer32
    MAX-ACCESS  read-only
    STATUS      current
    DESCRIPTION  "Current count of number of beacons received from member of BSS."
    ::= { arrisRouterAdvanceWirelessStatsRecv 39 }

arrisRouterRxWDSFrameCount OBJECT-TYPE
    SYNTAX      Integer32
    MAX-ACCESS  read-only
    STATUS      current
    DESCRIPTION  "Current count of number of unicast frames addressed to the MAC from other BSS (WDS FRAME)"
    ::= { arrisRouterAdvanceWirelessStatsRecv 40 }

arrisRouterRxOtherBeaconCount OBJECT-TYPE
    SYNTAX      Integer32
    MAX-ACCESS  read-only
    STATUS      current
    DESCRIPTION  "Current count of number of beacons received from other BSS."
    ::= { arrisRouterAdvanceWirelessStatsRecv 41 }

arrisRouterRxTimeoutsCount OBJECT-TYPE
    SYNTAX      Integer32
    MAX-ACCESS  read-only
    STATUS      current
    DESCRIPTION  "Current count of number of response timeouts for transmitted frames expecting a response."
    ::= { arrisRouterAdvanceWirelessStatsRecv 42 }

arrisRouterRxFiFoZeroOverflows OBJECT-TYPE
    SYNTAX      Integer32
    MAX-ACCESS  read-only
    STATUS      current
    DESCRIPTION  "Current count of receive fifo 0 overflows."
    ::= { arrisRouterAdvanceWirelessStatsRecv 43 }

arrisRouterRxFiFoOneOverflows OBJECT-TYPE
    SYNTAX      Integer32
    MAX-ACCESS  read-only
    STATUS      current
    DESCRIPTION  "Current count of receive fifo 1 overflows."
    ::= { arrisRouterAdvanceWirelessStatsRecv 44 }

arrisRouterRxFiFoTwoOverflows OBJECT-TYPE
    SYNTAX      Integer32
    MAX-ACCESS  read-only
    STATUS      current
    DESCRIPTION  "Current count of receive fifo 2 overflows."
    ::= { arrisRouterAdvanceWirelessStatsRecv 45 }

arrisRouterRxPRQFIFOCount OBJECT-TYPE
    SYNTAX      Integer32
    MAX-ACCESS  read-only
    STATUS      current
    DESCRIPTION  "Number of received Probe requests that made it into the Probe Request Queue FIFO."
    ::= { arrisRouterAdvanceWirelessStatsRecv 46 }

arrisRouterRxPRQOverflowCount OBJECT-TYPE
    SYNTAX      Integer32
    MAX-ACCESS  read-only
    STATUS      current
    DESCRIPTION  "Number of receive Probe Request Queue overflows in the AP."
    ::= { arrisRouterAdvanceWirelessStatsRecv 47 }

arrisRouterRxAfterburnerNACKCount OBJECT-TYPE
    SYNTAX      Integer32
    MAX-ACCESS  read-only
    STATUS      current
    DESCRIPTION  "Number of NACK Afterburner frames received."
    ::= { arrisRouterAdvanceWirelessStatsRecv 48 }

arrisRouterRxAfterburnerConsumedCount OBJECT-TYPE
    SYNTAX      Integer32
    MAX-ACCESS  read-only
    STATUS      current
    DESCRIPTION  "Number of frames completed without transmission because of an Afterburner re-queue."
    ::= { arrisRouterAdvanceWirelessStatsRecv 49 }

arrisRouterRxFrameDuplicateCount OBJECT-TYPE
    SYNTAX      Integer32
    MAX-ACCESS  read-only
    STATUS      current
    DESCRIPTION  "This counter shall increment when a frame is received that the Sequence Control field indicates is a duplicate."
    ::= { arrisRouterAdvanceWirelessStatsRecv 50 }

arrisRouterRxFragmentCount OBJECT-TYPE
    SYNTAX      Integer32
    MAX-ACCESS  read-only
    STATUS      current
    DESCRIPTION  "This counter shall be incremented for each successfully received MPDU of type Data or Management."
    ::= { arrisRouterAdvanceWirelessStatsRecv 51 }

arrisRouterRxMulticastCount OBJECT-TYPE
    SYNTAX      Integer32
    MAX-ACCESS  read-only
    STATUS      current
    DESCRIPTION  "This counter shall increment when a MSDU is received with the multicast bit set in the destination MAC address."
    ::= { arrisRouterAdvanceWirelessStatsRecv 52 }

arrisRouterRxFCSErrorCount OBJECT-TYPE
    SYNTAX      Integer32
    MAX-ACCESS  read-only
    STATUS      current
    DESCRIPTION  "This counter shall increment when an FCS error is detected in a received MPDU."
    ::= { arrisRouterAdvanceWirelessStatsRecv 53 }

arrisRouterWEPUndecryptableCount OBJECT-TYPE
    SYNTAX      Integer32
    MAX-ACCESS  read-only
    STATUS      current
    DESCRIPTION  "This counter shall increment when a frame is received with the WEP subfield of the Frame Control field set to one
                    and the WEPOn value for the key mapped to the TA's MAC address indicates that the frame should not have been encrypted or that frame
                    is discarded due to the receiving STA not implementing the privacy option."
    ::= { arrisRouterAdvanceWirelessStatsEncrypt 1 }

arrisRouterTKIPLocalMICFailureCount OBJECT-TYPE
    SYNTAX      Integer32
    MAX-ACCESS  read-only
    STATUS      current
    DESCRIPTION  "Count of local Message Integrity Check (MIC) failures for TKIP."
    ::= { arrisRouterAdvanceWirelessStatsEncrypt 2 }

arrisRouterTKIPCounterMeasuresInvoked OBJECT-TYPE
    SYNTAX      Integer32
    MAX-ACCESS  read-only
    STATUS      current
    DESCRIPTION  "Count of number of times TKIP counter measures have been invoked."
    ::= { arrisRouterAdvanceWirelessStatsEncrypt 3 }

arrisRouterTKIPReplayCount OBJECT-TYPE
    SYNTAX      Integer32
    MAX-ACCESS  read-only
    STATUS      current
    DESCRIPTION  "TKIP replay count."
    ::= { arrisRouterAdvanceWirelessStatsEncrypt 4 }

arrisRouterAESFormatErrorCount OBJECT-TYPE
    SYNTAX      Integer32
    MAX-ACCESS  read-only
    STATUS      current
    DESCRIPTION  "The current number of AES format errors."
    ::= { arrisRouterAdvanceWirelessStatsEncrypt 5 }

arrisRouterAESReplaysCount OBJECT-TYPE
    SYNTAX      Integer32
    MAX-ACCESS  read-only
    STATUS      current
    DESCRIPTION  "The current number of AES replays."
    ::= { arrisRouterAdvanceWirelessStatsEncrypt 6 }

arrisRouterAESDecryptErrorCount OBJECT-TYPE
    SYNTAX      Integer32
    MAX-ACCESS  read-only
    STATUS      current
    DESCRIPTION  "The current number of AES decrypt errors."
    ::= { arrisRouterAdvanceWirelessStatsEncrypt 7 }

arrisRouterFourWayHandshakeFails OBJECT-TYPE
    SYNTAX      Integer32
    MAX-ACCESS  read-only
    STATUS      current
    DESCRIPTION  "The current number of four-way handshake failures."
    ::= { arrisRouterAdvanceWirelessStatsEncrypt 8 }

arrisRouterWEPPICVErrorCount OBJECT-TYPE
    SYNTAX      Integer32
    MAX-ACCESS  read-only
    STATUS      current
    DESCRIPTION  "The current number of WEP PICV errors."
    ::= { arrisRouterAdvanceWirelessStatsEncrypt 9 }

arrisRouterDecryptSuccessCount OBJECT-TYPE
    SYNTAX      Integer32
    MAX-ACCESS  read-only
    STATUS      current
    DESCRIPTION  "The decrypt success count."
    ::= { arrisRouterAdvanceWirelessStatsEncrypt 10 }

arrisRouterTKIPPICVErrorCount OBJECT-TYPE
    SYNTAX      Integer32
    MAX-ACCESS  read-only
    STATUS      current
    DESCRIPTION  "The current number of TKIP PICV errors."
    ::= { arrisRouterAdvanceWirelessStatsEncrypt 11 }

arrisRouterWEPExcludedCount OBJECT-TYPE
    SYNTAX      Integer32
    MAX-ACCESS  read-only
    STATUS      current
    DESCRIPTION  "The current number of WEP frames that were excluded."
    ::= { arrisRouterAdvanceWirelessStatsEncrypt 12 }



arrisRouterPacketsRcv1Mbps OBJECT-TYPE
    SYNTAX      Integer32
    MAX-ACCESS  read-only
    STATUS      current
    DESCRIPTION  "The current number of packets received at 1 Mbps."
    ::= { arrisRouterAdvanceWirelessStatsRateStats 1 }

arrisRouterPacketsRcv2Mbps OBJECT-TYPE
    SYNTAX      Integer32
    MAX-ACCESS  read-only
    STATUS      current
    DESCRIPTION  "The current number of packets received at 2 Mbps."
    ::= { arrisRouterAdvanceWirelessStatsRateStats 2 }

arrisRouterPacketsRcv5HalfMbps OBJECT-TYPE
    SYNTAX      Integer32
    MAX-ACCESS  read-only
    STATUS      current
    DESCRIPTION  "The current number of packets received at 5.5 Mbps."
    ::= { arrisRouterAdvanceWirelessStatsRateStats 3 }

arrisRouterPacketsRcv6Mbps OBJECT-TYPE
    SYNTAX      Integer32
    MAX-ACCESS  read-only
    STATUS      current
    DESCRIPTION  "The current number of packets received at 6 Mbps."
    ::= { arrisRouterAdvanceWirelessStatsRateStats 4 }

arrisRouterPacketsRcv9Mbps OBJECT-TYPE
    SYNTAX      Integer32
    MAX-ACCESS  read-only
    STATUS      current
    DESCRIPTION  "The current number of packets received at 9 Mbps."
    ::= { arrisRouterAdvanceWirelessStatsRateStats 5 }

arrisRouterPacketsRcv11Mbps OBJECT-TYPE
    SYNTAX      Integer32
    MAX-ACCESS  read-only
    STATUS      current
    DESCRIPTION  "The current number of packets received at 11 Mbps."
    ::= { arrisRouterAdvanceWirelessStatsRateStats 6 }

arrisRouterPacketsRcv12Mbps OBJECT-TYPE
    SYNTAX      Integer32
    MAX-ACCESS  read-only
    STATUS      current
    DESCRIPTION  "The current number of packets received at 12 Mbps."
    ::= { arrisRouterAdvanceWirelessStatsRateStats 7 }

arrisRouterPacketsRcv18Mbps OBJECT-TYPE
    SYNTAX      Integer32
    MAX-ACCESS  read-only
    STATUS      current
    DESCRIPTION  "The current number of packets received at 18 Mbps."
    ::= { arrisRouterAdvanceWirelessStatsRateStats 8 }

arrisRouterPacketsRcv24Mbps OBJECT-TYPE
    SYNTAX      Integer32
    MAX-ACCESS  read-only
    STATUS      current
    DESCRIPTION  "The current number of packets received at 24 Mbps."
    ::= { arrisRouterAdvanceWirelessStatsRateStats 9 }

arrisRouterPacketsRcv36Mbps OBJECT-TYPE
    SYNTAX      Integer32
    MAX-ACCESS  read-only
    STATUS      current
    DESCRIPTION  "The current number of packets received at 36 Mbps."
    ::= { arrisRouterAdvanceWirelessStatsRateStats 10 }

arrisRouterPacketsRcv48Mbps OBJECT-TYPE
    SYNTAX      Integer32
    MAX-ACCESS  read-only
    STATUS      current
    DESCRIPTION  "The current number of packets received at 48 Mbps."
    ::= { arrisRouterAdvanceWirelessStatsRateStats 11 }

arrisRouterPacketsRcv54Mbps OBJECT-TYPE
    SYNTAX      Integer32
    MAX-ACCESS  read-only
    STATUS      current
    DESCRIPTION  "The current number of packets received at 54 Mbps."
    ::= { arrisRouterAdvanceWirelessStatsRateStats 12 }

arrisRouterPacketsRcv108Mbps OBJECT-TYPE
    SYNTAX      Integer32
    MAX-ACCESS  read-only
    STATUS      current
    DESCRIPTION  "The current number of packets received at 108 Mbps."
    ::= { arrisRouterAdvanceWirelessStatsRateStats 13 }

arrisRouterPacketsRcv162Mbps OBJECT-TYPE
    SYNTAX      Integer32
    MAX-ACCESS  read-only
    STATUS      current
    DESCRIPTION  "The current number of packets received at 162 Mbps."
    ::= { arrisRouterAdvanceWirelessStatsRateStats 14 }

arrisRouterPacketsRcv216Mbps OBJECT-TYPE
    SYNTAX      Integer32
    MAX-ACCESS  read-only
    STATUS      current
    DESCRIPTION  "The current number of packets received at 216 Mbps."
    ::= { arrisRouterAdvanceWirelessStatsRateStats 15 }

arrisRouterPacketsRcv270Mbps OBJECT-TYPE
    SYNTAX      Integer32
    MAX-ACCESS  read-only
    STATUS      current
    DESCRIPTION  "The current number of packets received at 270 Mbps."
    ::= { arrisRouterAdvanceWirelessStatsRateStats 16 }

arrisRouterPacketsRcv324Mbps OBJECT-TYPE
    SYNTAX      Integer32
    MAX-ACCESS  read-only
    STATUS      current
    DESCRIPTION  "The current number of packets received at 324 Mbps."
    ::= { arrisRouterAdvanceWirelessStatsRateStats 17 }

arrisRouterPacketsRcv378Mbps OBJECT-TYPE
    SYNTAX      Integer32
    MAX-ACCESS  read-only
    STATUS      current
    DESCRIPTION  "The current number of packets received at 378 Mbps."
    ::= { arrisRouterAdvanceWirelessStatsRateStats 18 }

arrisRouterPacketsRcv432Mbps OBJECT-TYPE
    SYNTAX      Integer32
    MAX-ACCESS  read-only
    STATUS      current
    DESCRIPTION  "The current number of packets received at 432 Mbps."
    ::= { arrisRouterAdvanceWirelessStatsRateStats 19 }

arrisRouterPacketsRcv486Mbps OBJECT-TYPE
    SYNTAX      Integer32
    MAX-ACCESS  read-only
    STATUS      current
    DESCRIPTION  "The current number of packets received at 486 Mbps."
    ::= { arrisRouterAdvanceWirelessStatsRateStats 20 }

arrisRouterPacketsRcv540Mbps OBJECT-TYPE
    SYNTAX      Integer32
    MAX-ACCESS  read-only
    STATUS      current
    DESCRIPTION  "The current number of packets received at 540 Mbps."
    ::= { arrisRouterAdvanceWirelessStatsRateStats 21 }

----
arrisRouterResetCount OBJECT-TYPE
    SYNTAX      Integer32
    MAX-ACCESS  read-only
    STATUS      current
    DESCRIPTION  "Current count of driver resets."
    ::= { arrisRouterAdvanceWirelessStats 5 }

arrisRouterTBTTCount OBJECT-TYPE
    SYNTAX      Integer32
    MAX-ACCESS  read-only
    STATUS      current
    DESCRIPTION  "Current count of TBTT interrupts."
    ::= { arrisRouterAdvanceWirelessStats 6 }

arrisRouterPMQOverflowCount OBJECT-TYPE
    SYNTAX      Integer32
    MAX-ACCESS  read-only
    STATUS      current
    DESCRIPTION  "Current count of Number of PMQ overflows."
    ::= { arrisRouterAdvanceWirelessStats 7 }

arrisRouterPRTimeoutDropCount OBJECT-TYPE
    SYNTAX      Integer32
    MAX-ACCESS  read-only
    STATUS      current
    DESCRIPTION  "Number of probe requests that were dropped from the PRQ fifo because a probe response could not be sent out within the time limit defined in M_PRS_MAXTIMe."
    ::= { arrisRouterAdvanceWirelessStats 8 }

arrisRouterPSMWatchdogCount OBJECT-TYPE
    SYNTAX      Integer32
    MAX-ACCESS  read-only
    STATUS      current
    DESCRIPTION  "The count of PSM watchdogs."
    ::= { arrisRouterAdvanceWirelessStats 9 }

arrisRouterPHYWatchdogCount OBJECT-TYPE
    SYNTAX      Integer32
    MAX-ACCESS  read-only
    STATUS      current
    DESCRIPTION  "The count of PHY-layer watchdogs."
    ::= { arrisRouterAdvanceWirelessStats 10 }

arrisRouterPRQEntriesHandled OBJECT-TYPE
    SYNTAX      Integer32
    MAX-ACCESS  read-only
    STATUS      current
    DESCRIPTION  "The count of PRQ entries read in."
    ::= { arrisRouterAdvanceWirelessStats 11 }

arrisRouterPRQUndirectedEntriesHandled OBJECT-TYPE
    SYNTAX      Integer32
    MAX-ACCESS  read-only
    STATUS      current
    DESCRIPTION  "The count of PRQ entries which were broadcast BSS & SSID."
    ::= { arrisRouterAdvanceWirelessStats 12 }

arrisRouterPRQBadEntriesHandled OBJECT-TYPE
    SYNTAX      Integer32
    MAX-ACCESS  read-only
    STATUS      current
    DESCRIPTION  "The count of PRQ entries which could not be translated to information."
    ::= { arrisRouterAdvanceWirelessStats 13 }

arrisRouterATIMSuppressCount OBJECT-TYPE
    SYNTAX      Integer32
    MAX-ACCESS  read-only
    STATUS      current
    DESCRIPTION  "The count of transmit suppressions on ATIM FIFO."
    ::= { arrisRouterAdvanceWirelessStats 14 }

arrisRouterBCNTemplateNotReadyCount OBJECT-TYPE
    SYNTAX      Integer32
    MAX-ACCESS  read-only
    STATUS      current
    DESCRIPTION  "The count of Template frames marked in use on send bcn."
    ::= { arrisRouterAdvanceWirelessStats 15 }

arrisRouterBCNTemplateNotReadyDoneCount OBJECT-TYPE
    SYNTAX      Integer32
    MAX-ACCESS  read-only
    STATUS      current
    DESCRIPTION  "The count of Template frames marked in use on send bcn but 'DMA done' interrupt received."
    ::= { arrisRouterAdvanceWirelessStats 16 }

arrisRouterLateTBTTDPCCount OBJECT-TYPE
    SYNTAX      Integer32
    MAX-ACCESS  read-only
    STATUS      current
    DESCRIPTION  "The count of TBTT DPC that did not happen in time."
    ::= { arrisRouterAdvanceWirelessStats 17 }

arrisRouterPktEngineUnicastRxFramesCount OBJECT-TYPE
    SYNTAX      Integer32
    MAX-ACCESS  read-only
    STATUS      current
    DESCRIPTION  "The number of unicast frames received by the packet engine code."
    ::= { arrisRouterAdvanceWirelessStats 18 }

arrisRouterPktEngineMulticastRxFramesCount OBJECT-TYPE
    SYNTAX      Integer32
    MAX-ACCESS  read-only
    STATUS      current
    DESCRIPTION  "The number of multicast frames received by the packet engine code."
    ::= { arrisRouterAdvanceWirelessStats 19 }

arrisRouterRadioDisablesCount OBJECT-TYPE
    SYNTAX      Integer32
    MAX-ACCESS  read-only
    STATUS      current
    DESCRIPTION  "The number of radio disables."
    ::= { arrisRouterAdvanceWirelessStats 20 }

arrisRouterBPHYGlitchCount OBJECT-TYPE
    SYNTAX      Integer32
    MAX-ACCESS  read-only
    STATUS      current
    DESCRIPTION  "The PHY count of bphy glitches."
    ::= { arrisRouterAdvanceWirelessStats 21 }

arrisRouterSGITransmitCount OBJECT-TYPE
    SYNTAX      Integer32
    MAX-ACCESS  read-only
    STATUS      current
    DESCRIPTION  "The count for SGI transmit."
    ::= { arrisRouterAdvanceWirelessStats 22 }

arrisRouterSGIReceiveCount OBJECT-TYPE
    SYNTAX      Integer32
    MAX-ACCESS  read-only
    STATUS      current
    DESCRIPTION  "The count for SGI receive."
    ::= { arrisRouterAdvanceWirelessStats 23 }

arrisRouterSTBCTransmitCount OBJECT-TYPE
    SYNTAX      Integer32
    MAX-ACCESS  read-only
    STATUS      current
    DESCRIPTION  "The count for STBC transmit."
    ::= { arrisRouterAdvanceWirelessStats 24 }

arrisRouterSTBCReceiveCount OBJECT-TYPE
    SYNTAX      Integer32
    MAX-ACCESS  read-only
    STATUS      current
    DESCRIPTION  "The count for STBC receive."
    ::= { arrisRouterAdvanceWirelessStats 25 }

arrisRouterAdvWiFiStatsRadio OBJECT-TYPE
    SYNTAX      INTEGER { radio0(0), radio1(1) }
    MAX-ACCESS  read-write
    STATUS      current
    DESCRIPTION  "The radio to use when querying all advanced wireless stats under arrisRouterAdvanceWirelessStats."
    DEFVAL { radio0 }
    ::= { arrisRouterAdvanceWirelessStats 26 }

arrisRouterWiFiInterferencePhyLayer OBJECT-TYPE
     SYNTAX      INTEGER { disabled(0), nonWirelessInterferenceMitigation(1),  wirelessInterferenceMitigation(2), autoWirelessInterferenceMitigation(3), autoWirelessInterferenceMitigationAndNoiseReduction(4) }
     MAX-ACCESS  read-write
     STATUS      current
     DESCRIPTION "Get/set the wireless interference setting at the physical layer."
     DEFVAL { disabled }
     ::= { arrisRouterWirelessCfg 47 }

arrisRouterWiFiInterferenceDriverLayer OBJECT-TYPE
     SYNTAX      INTEGER { off(0), detectOnly(1), detectAndAct(2) }
     MAX-ACCESS  read-write
     STATUS      current
     DESCRIPTION "Get/set the wireless interference setting at the driver layer.  This value is the one that should used to try and mitigate interference from other 802.11 APs."
     DEFVAL { detectOnly }
     ::= { arrisRouterWirelessCfg 48 }

arrisRouterWiFiChannelsInterferenceState OBJECT-TYPE
     SYNTAX      DisplayString
     MAX-ACCESS  read-only
     STATUS      current
     DESCRIPTION "Get the wireless interference state for channels 1-14. The interference state for each channel is either 'OK' or 'SEVERE'.
                The interference state for all channels is returned as a string, i.e. 1=OK 2=OK 3=OK 4=OK 5=OK 6=SEVERE 7=OK 8=OK 9=OK 10=OK 11=OK 12=OK 13=OK 14=Ok."
     ::= { arrisRouterWirelessCfg 49 }


-- OIDs for 5 Ghz radio for devices with dual-bands


arrisRouterWiFi50RadioSettings OBJECT IDENTIFIER ::= { arrisRouterWirelessCfg 50 }

arrisRouterWiFi50Channel OBJECT-TYPE
     SYNTAX     Unsigned32 (0..216)
     MAX-ACCESS  read-write
     STATUS      current
     DESCRIPTION  "Controls and reflects the current channel number on the 5.0 GHz radio (802.11 a/n).

				 If set to (0), the device will be put in auto-channel mode where it automatically scans
				 for the least-crowded channel.

				 Available channels are 34-216.
				 Channel selection is also subject to restrictions based on the selected
				 country code."
     ::= { arrisRouterWiFi50RadioSettings 1 }

arrisRouterWiFi50Mode OBJECT-TYPE
     SYNTAX      INTEGER { unknown(-1), anMix(0), aOnly(1), nOnly(4), acOnly(5), nacMix(6), anacMix(7) }
     MAX-ACCESS  read-write
     STATUS      current
     DESCRIPTION "Controls and reflects the behavior of the device with regards to which flavor of 802.11 is used."
     ::= { arrisRouterWiFi50RadioSettings 2 }

arrisRouterWiFi50BeaconInterval OBJECT-TYPE
     SYNTAX      Unsigned32 (1..65535)
     UNITS		 "milliseconds"
     MAX-ACCESS  read-write
     STATUS      current
     DESCRIPTION "Amount of time between beacon transmissions."
     DEFVAL { 100 }
     ::= { arrisRouterWiFi50RadioSettings 3 }

arrisRouterWiFi50DTIMInterval OBJECT-TYPE
     SYNTAX      Unsigned32 (1..255)
     UNITS		 "milliseconds"
     MAX-ACCESS  read-write
     STATUS      current
     DESCRIPTION "Amount of time between Delivery Traffic Indication Messages."
     DEFVAL { 1 }
     ::= { arrisRouterWiFi50RadioSettings 4 }

arrisRouterWiFi50TxPreamble OBJECT-TYPE
     SYNTAX      INTEGER { unknown(-1), long(0), short(1) }
     MAX-ACCESS  read-write
     STATUS      current
     DESCRIPTION "This attribute, indicates whether the transfer preamble is long or short."
     DEFVAL { 0 }
     ::= { arrisRouterWiFi50RadioSettings 5 }

arrisRouterWiFi50RTSThreshold OBJECT-TYPE
     SYNTAX      Unsigned32 (0..2347)
     UNITS       "bytes"
     MAX-ACCESS  read-write
     STATUS      current
     DESCRIPTION
		"The RTS (Request to Send) Threshold indicates the number of bytes in an MPDU,
        below which an RTS/CTS handshake shall not be performed. An RTS/CTS handshake shall
        be performed at the beginning of any frame exchange sequence where the MPDU is of type Data or
        Management, the MPDU has an individual address in the Address1 field, and the length of the MPDU is greater than
        this threshold. Setting this attribute to be larger than the maximum MSDU size shall have the effect of
        turning off the RTS/CTS handshake for frames of Data or Management type transmitted by
        this device. Setting this attribute to zero shall have the effect of turning on the RTS/CTS handshake for
        all frames of Data or Management type transmitted by this device. "
     DEFVAL { 2347 }
     ::= { arrisRouterWiFi50RadioSettings 6 }

arrisRouterWiFi50FragmentThresh OBJECT-TYPE
     SYNTAX      Unsigned32 (256..2346)
     UNITS       "bytes"
     MAX-ACCESS  read-write
     STATUS      current
     DESCRIPTION "This value specifies the maximum size of a packet before the data is fragmented into two or more packets."
     DEFVAL { 2346 }
     ::= { arrisRouterWiFi50RadioSettings 7 }

arrisRouterWiFi50ShortSlot OBJECT-TYPE
     SYNTAX      TruthValue
     MAX-ACCESS  read-write
     STATUS      current
     DESCRIPTION "This returns whether or not the use of short slot timing mode is on or off (long).
                    The amount of time a device waits after a collision before retransmitting a packet.
                    You can increase throughput by enabling short slot time.
                    Use the new arrisRouterWiFiShortSlotEnhanced to set to 'auto' mode."
     DEFVAL { true }
     ::= { arrisRouterWiFi50RadioSettings 8 }

arrisRouterWiFi50FrameBurst OBJECT-TYPE
     SYNTAX      TruthValue
     MAX-ACCESS  read-write
     STATUS      current
     DESCRIPTION "Bursting may increase the throughput of link connection in certain
					conditions. This can result in the ability to support higher data
					throughput in mixed and uniform networks. Also known as 'XPress Technology'"
     DEFVAL { false }
     ::= { arrisRouterWiFi50RadioSettings 9 }

arrisRouterWiFi50EnableRadio OBJECT-TYPE
     SYNTAX      TruthValue
     MAX-ACCESS  read-write
     STATUS      current
     DESCRIPTION "Enable or disable 5 GHz WiFi radio."
     DEFVAL { true }
     ::= { arrisRouterWiFi50RadioSettings 10 }

arrisRouterWiFi50TxPower OBJECT-TYPE
     SYNTAX      Integer32 (1..8)
     MAX-ACCESS  read-write
     STATUS      current
     DESCRIPTION "The TxPowerLevel N currently being used to transmit data.
                  Some PHYs also use this value to determine the receiver
                  sensitivity requirements for CCA. Note that 0 indicates the value can't be read."
     ::= { arrisRouterWiFi50RadioSettings 11 }

arrisRouterWiFi50ShortRetryLimit OBJECT-TYPE
     SYNTAX      Integer32 (1..255)
     MAX-ACCESS  read-write
     STATUS      current
     DESCRIPTION "Get or set the retry limit of frames longer than the RTS threshold."
     ::= { arrisRouterWiFi50RadioSettings 12 }

arrisRouterWiFi50LongRetryLimit OBJECT-TYPE
     SYNTAX      Integer32 (1..255)
     MAX-ACCESS  read-write
     STATUS      current
     DESCRIPTION "Get or set the retry limit of frames shorter than the RTS threshold."
     ::= { arrisRouterWiFi50RadioSettings 13 }

arrisRouterWiFi50OutputPower OBJECT-TYPE
    SYNTAX      INTEGER {
                percent12(12),
                percent25(25),
                percent50(50),
                percent75(75),
                percent100(100)
    }
    MAX-ACCESS  read-write
    STATUS      current
    DESCRIPTION
        "Sets the output power relative to the hardware's maximum capability.
	 Now only percent25(25), percent50(50) and percent100(100) can be set,
	 they are mapped to Low, medium and high power level which used on GUI."
    DEFVAL { percent100 }
    ::= { arrisRouterWiFi50RadioSettings 14 }

arrisRouterWiFi50MulticastA OBJECT-TYPE
     SYNTAX		 INTEGER {	auto(0),
							rate12mbps(12),
							rate18mbps(18),
							rate24mbps(24),
							rate36mbps(36),
							rate48mbps(48),
							rate72mbps(72),
							rate96mbps(96),
							rate108mbps(108)
							}
     MAX-ACCESS  read-write
     STATUS      current
     DESCRIPTION "Get or set the multicast rate for 802.11a."
     ::= { arrisRouterWiFi50RadioSettings 15 }

arrisRouterWiFi50PhysicalChannel OBJECT-TYPE
    SYNTAX      Integer32
    MAX-ACCESS  read-only
    STATUS      current
    DESCRIPTION  "The current channel the 5.0 GHz WiFi radio is using.
                  This may match arrisRouterWiFiChannel except when that value is auto(0).
                  When the 'auto' mode is used, this OID will return the actual channel being used."
    ::= { arrisRouterWiFi50RadioSettings 16 }

arrisRouterWiFi50TxPowerPhysical OBJECT-TYPE
    SYNTAX      Integer32
    UNITS       "qdbm"
    MAX-ACCESS  read-only
    STATUS      current
    DESCRIPTION  "The current measured transmit power 5.0 GHz radio.  Divide by 4 to convert to dbm."
    ::= { arrisRouterWiFi50RadioSettings 17 }

arrisRouterWiFi50PhysicalChannelDetails OBJECT-TYPE
    SYNTAX      DisplayString
    MAX-ACCESS  read-only
    STATUS      current
    DESCRIPTION  "The current channel the 5.0 GHz WiFi radio is using."
    ::= { arrisRouterWiFi50RadioSettings 18 }

arrisRouterWiFi50NSettings OBJECT IDENTIFIER ::= { arrisRouterWiFi50RadioSettings 20 }

arrisRouterWiFi50HTMCS OBJECT-TYPE
     SYNTAX  INTEGER { auto(0),
					  legacy(1),
					  mcs0(2),
					  mcs1(3),
					  mcs2(4),
					  mcs3(5),
					  mcs4(6),
					  mcs5(7),
					  mcs6(8),
					  mcs7(9),
					  mcs8(10),
					  mcs9(11),
					  mcs10(12),
					  mcs11(13),
					  mcs12(14),
					  mcs13(15),
					  mcs14(16),
					  mcs15(17),
                                          mcs16(18),
                                          mcs17(19),
                                          mcs18(20),
                                          mcs19(21),
                                          mcs20(22),
                                          mcs21(23),
                                          mcs22(24),
                                          mcs23(25)
					}
     MAX-ACCESS  read-write
     STATUS      current
     DESCRIPTION "Get or set the 802.11n physical modulation coding scheme (MCS) rate.
				Forces the N Phy transmission rate for the AP to a particular speed.
				Each group of rates corresponds to BW (20 MHz or 40 MHz) and GI (800ns or 400ns) configuration.
				mcs0:	6.5   Mbps for 20Mhz and	13.5  Mbps for 40 MHz if guard interval is 800ns.
						7.2   Mbps for 20Mhz and	15    Mbps for 40 Mhz if guard interval is 400ns.
				mcs1:	13    Mbps for 20Mhz and	27    Mbps for 40 MHz if guard interval is 800ns.
						14.4  Mbps for 20Mhz and	30    Mbps for 40 Mhz if guard interval is 400ns.
				mcs2:	19.5  Mbps for 20Mhz and	40.5  Mbps for 40 MHz if guard interval is 800ns.
						21.7  Mbps for 20Mhz and	45    Mbps for 40 Mhz if guard interval is 400ns.
				mcs3:	26    Mbps for 20Mhz and	54    Mbps for 40 MHz if guard interval is 800ns.
						28.9  Mbps for 20Mhz and	60    Mbps for 40 Mhz if guard interval is 400ns.
				mcs4:	39    Mbps for 20Mhz and	81    Mbps for 40 MHz if guard interval is 800ns.
						43.3  Mbps for 20Mhz and	90    Mbps for 40 Mhz if guard interval is 400ns.
				mcs5:	52    Mbps for 20Mhz and	108   Mbps for 40 MHz if guard interval is 800ns.
						57.8  Mbps for 20Mhz and	120   Mbps for 40 Mhz if guard interval is 400ns.
				mcs6:	58.5  Mbps for 20Mhz and	121.5 Mbps for 40 MHz if guard interval is 800ns.
						65    Mbps for 20Mhz and	135   Mbps for 40 Mhz if guard interval is 400ns.
				mcs7:	65    Mbps for 20Mhz and	135   Mbps for 40 MHz if guard interval is 800ns.
						72.2  Mbps for 20Mhz and	150   Mbps for 40 Mhz if guard interval is 400ns.
				mcs8:	13    Mbps for 20Mhz and	27    Mbps for 40 MHz if guard interval is 800ns.
						14.4  Mbps for 20Mhz and	30    Mbps for 40 Mhz if guard interval is 400ns.
				mcs9:	26    Mbps for 20Mhz and	54    Mbps for 40 MHz if guard interval is 800ns.
						28.9  Mbps for 20Mhz and	60    Mbps for 40 Mhz if guard interval is 400ns.
				mcs10:	39    Mbps for 20Mhz and	81    Mbps for 40 MHz if guard interval is 800ns.
						43.3  Mbps for 20Mhz and	90    Mbps for 40 Mhz if guard interval is 400ns.
				mcs11:	52    Mbps for 20Mhz and	108   Mbps for 40 MHz if guard interval is 800ns.
						57.8  Mbps for 20Mhz and	120   Mbps for 40 Mhz if guard interval is 400ns.
				mcs12:	78    Mbps for 20Mhz and	162   Mbps for 40 MHz if guard interval is 800ns.
						86.7  Mbps for 20Mhz and	180   Mbps for 40 Mhz if guard interval is 400ns.
				mcs13:	104   Mbps for 20Mhz and	216   Mbps for 40 MHz if guard interval is 800ns.
						115.6 Mbps for 20Mhz and	240   Mbps for 40 Mhz if guard interval is 400ns.
				mcs14:	117   Mbps for 20Mhz and	243   Mbps for 40 MHz if guard interval is 800ns.
						130.3 Mbps for 20Mhz and	270   Mbps for 40 Mhz if guard interval is 400ns.
				mcs15:	130   Mbps for 20Mhz and	270   Mbps for 40 MHz if guard interval is 800ns.
						144.4 Mbps for 20Mhz and	300   Mbps for 40 Mhz if guard interval is 400ns.
				mcs16 ~ mcs23 are also suppported
                                "
     ::= { arrisRouterWiFi50NSettings 1 }

arrisRouterWiFi50ChannelBW OBJECT-TYPE
     SYNTAX      INTEGER { unknown(-1), width20MHz(0), width40MHz(1), width20and40Mhz(2), width20and40and80Mhz(3) }
     MAX-ACCESS  read-write
     STATUS      current
     DESCRIPTION "Determines which Band Width that we will be operating in. Either the 20MHz 40MHz or the 80MHz.
                  Note: This is for 802.11n mode only. "
     ::= { arrisRouterWiFi50NSettings 2 }

arrisRouterWiFi50NSideBand OBJECT-TYPE
    SYNTAX      INTEGER {
		unknown(-1),
		upper(1),
		lower(2)
    }
    MAX-ACCESS  read-write
    STATUS      current
    DESCRIPTION
        "Determines which side Band the channel will operate in.
		Note: This is for 802.11n mode only, this OID is dependent on what arrisRouterWiFiChannelBW is selected and only
		applies when 40MHz is selected."
    ::= { arrisRouterWiFi50NSettings 3 }

arrisRouterWiFi50HTMode OBJECT-TYPE
     SYNTAX      INTEGER { mixed(0), greenField(1) }
     MAX-ACCESS  read-write
     STATUS      current
     DESCRIPTION "In mixed mode, each 802.11n transmission is always embedded in an 802.11a or 802.11g transmission.
				 Green field will ingore some of the early standard, so 802.11n devices have higher efficiency but 802.11a/b/g devices
				 can not use this network in greenfield mode."
	 DEFVAL { 0 }
     ::= { arrisRouterWiFi50NSettings 4 }

arrisRouterWiFi50GuardInterval OBJECT-TYPE
     SYNTAX      INTEGER { gi400(0), gi800(1), auto(2) }
     MAX-ACCESS  read-write
     STATUS      current
     DESCRIPTION "Spacing between transmission of symbols in nanoseconds."
     DEFVAL { gi800 }
     ::= { arrisRouterWiFi50NSettings 5 }

arrisRouterWiFi50AMSDUEnable OBJECT-TYPE
     SYNTAX      TruthValue
     MAX-ACCESS  read-write
     STATUS      current
     DESCRIPTION "Aggregation of MAC Service Data Units (MSDUs) at the top of the MAC."
     DEFVAL { false }
     ::= { arrisRouterWiFi50NSettings 6 }

arrisRouterWiFi50DeclinePeerBA OBJECT-TYPE
     SYNTAX      TruthValue
     MAX-ACCESS  read-write
     STATUS      current
     DESCRIPTION "Enable or disable rejection of peer BA-request."
     DEFVAL { false }
     ::= { arrisRouterWiFi50NSettings 7 }

arrisRouterWiFi50BlockAck OBJECT-TYPE
     SYNTAX      TruthValue
     MAX-ACCESS  read-write
     STATUS      current
     DESCRIPTION "Enable or disable blocking of ACK (BA) during data transfer."
     DEFVAL { false }
     ::= { arrisRouterWiFi50NSettings 8 }

arrisRouterWiFi50NProtection OBJECT-TYPE
     SYNTAX      INTEGER { off(0), auto(1) }
     MAX-ACCESS  read-write
     STATUS      current
     DESCRIPTION "Set/read 802.11n protection setting. This is for OFDM protection for MIMO frames."
     ::= { arrisRouterWiFi50NSettings 9 }

arrisRouterWiFi50Allow40MHzOnlyOperation OBJECT-TYPE
     SYNTAX      TruthValue
     MAX-ACCESS  read-write
     STATUS      current
     DESCRIPTION "Allow the user to set 40 MHz only Wifi operation."
     DEFVAL { false }
     ::= { arrisRouterWiFi50NSettings 10 }

arrisRouterWiFi50HTTxStream OBJECT-TYPE
     SYNTAX     Unsigned32 (1..3)
     MAX-ACCESS  read-write
     STATUS      current
     DESCRIPTION  "Set or get the stream number on which the wireless antenna transmits."
     ::= { arrisRouterWiFi50RadioSettings 21 }

arrisRouterWiFi50HTRxStream OBJECT-TYPE
     SYNTAX     Unsigned32 (1..3)
     MAX-ACCESS  read-write
     STATUS      current
     DESCRIPTION  "Set or get the stream number on which the wireless antenna receives."
     ::= { arrisRouterWiFi50RadioSettings 22 }

arrisRouterWiFi50EnableSTBC OBJECT-TYPE
     SYNTAX      TruthValue
     MAX-ACCESS  read-write
     STATUS      current
     DESCRIPTION "Enable or disable Space Time Block Coding."
     DEFVAL { false }
     ::= { arrisRouterWiFi50RadioSettings 23 }

arrisRouterWiFi50EnableRDG OBJECT-TYPE
     SYNTAX      TruthValue
     MAX-ACCESS  read-write
     STATUS      current
     DESCRIPTION "Enable or disable Reverse Direction Grant."
     DEFVAL { false }
     ::= { arrisRouterWiFi50RadioSettings 24 }

arrisRouterWiFi50IGMPSnooping OBJECT-TYPE
     SYNTAX      TruthValue
     MAX-ACCESS  read-write
     STATUS      current
     DESCRIPTION "Enable or disable IGMP snooping.
                  When enabled it prevents unnecessary multicast traffic to the ports which did not subscribe to the multicast stream."
     DEFVAL { false }
     ::= { arrisRouterWiFi50RadioSettings 25 }

arrisRouterWiFi50BlockDFSChan OBJECT-TYPE
     SYNTAX      TruthValue
     MAX-ACCESS  read-write
     STATUS      current
     DESCRIPTION "Used to enable or disable the inclusion of DFS channels when configured to auto-select channels.
                  When enabled, it blocks DFS channels from being automatically selected.
                  When disabled, it allows DFS channels to be automatically selected."
     DEFVAL { true }
     ::= { arrisRouterWiFi50RadioSettings 26 }

arrisRouterWiFi50RTSRetry OBJECT-TYPE
    SYNTAX      INTEGER (0..255)
    MAX-ACCESS  read-write
    STATUS      current
    DESCRIPTION "Set or get the 5.0GHz RTS retry count. A non-zero value overrides the default RTS retry logic for single-client and multi-client.  If non-zero then the MIB value is the count used for RTS retries. Recommended value is between 1-32."
    DEFVAL {0}
    ::= { arrisRouterWiFi50RadioSettings 27 }

arrisRouterWiFi50TxRetry OBJECT-TYPE
    SYNTAX      INTEGER (0..255)
    MAX-ACCESS  read-write
    STATUS      current
    DESCRIPTION "Set or get the 5.0GHz Tx retry count.  A non-zero value overrides the default data Tx retry logic for single-client and multi-client.  If non-zero then the MIB value is the count used for data Tx retries. Recommended value is between 1-32."
    DEFVAL {0}
    ::= { arrisRouterWiFi50RadioSettings 28 }

arrisRouterWiFi50TransmitPowerInDecibel OBJECT-TYPE
     SYNTAX      INTEGER (0..28)
     UNITS       "Decibels"
     MAX-ACCESS  read-write
     STATUS      current
     DESCRIPTION "Sets the transmit power relative to the hardware's maximum capability.Configures Transmit Power in steps of 1dB for 5G radio"
     DEFVAL { 28 }
     ::= { arrisRouterWiFi50RadioSettings 30 }

arrisRouterWiFi50GUIDFSEn OBJECT-TYPE
     SYNTAX      TruthValue
     MAX-ACCESS  read-write
     STATUS      current
     DESCRIPTION "Enable or disable DFS channels can be selected in GUI."
     ::= { arrisRouterWiFi50RadioSettings 31 }

arrisRouterWiFi50StatsGatheringEnable OBJECT-TYPE
     SYNTAX      TruthValue
     MAX-ACCESS  read-write
     STATUS      current
     DESCRIPTION "Enable/Disable 5GHz stats gathering"
     DEFVAL { false }
     ::= { arrisRouterWiFi50RadioSettings 32 }

arrisRouterWiFi50AutoChannelList OBJECT-TYPE
     SYNTAX       DisplayString (SIZE(0..255))
     MAX-ACCESS   read-write
     STATUS       current
     DESCRIPTION  "Restricted available channel list for 5G radio (not all avail) from which to select a channel when arrisRouterWiFi50Channel
                   is set to auto-channel (0) mode. Space separated list. For 802.11a/n/ac, avail channels are 34-216. Channel selection also
                   subject to restriction based on the selected country code, using arrisRouterWiFiCountry. E.g. '36 48 165'. An empty string
                   denotes utilizing default country code channels. Channels included which are not part of the country code channels shall be ignored."
     ::= { arrisRouterWiFi50RadioSettings 33 }

arrisRouterWiFi50MgmtFramePower OBJECT-TYPE
     SYNTAX      Unsigned32(0..255)
     MAX-ACCESS  read-write
     STATUS      current
     DESCRIPTION "Configure the Management Frame Power value for all Frames. Power range from 0 to 255"
     DEFVAL { 255 }
     ::= { arrisRouterWiFi50RadioSettings 34 }

arrisRouterWiFi50GreenModeEnable OBJECT-TYPE
     SYNTAX      TruthValue
     MAX-ACCESS  read-write
     STATUS      current
     DESCRIPTION "Enable or Disable Green mode for WiFi radio(5GHz)."
     DEFVAL { false }
     ::= { arrisRouterWiFi50RadioSettings 35 }

arrisRouterWiFi50GreenModeStatus OBJECT-TYPE
     SYNTAX      INTEGER {
             none(0),
             active(1),
             inactive(2)
             }
     MAX-ACCESS  read-only
     STATUS      current
     DESCRIPTION  "Current status of WiFi 5GHz Green Mode."
     ::= { arrisRouterWiFi50RadioSettings 36}

arrisRouterWiFi50ExtensionChannel OBJECT-TYPE
      SYNTAX      INTEGER { belowControlChannel(0), aboveControlChannel(1), auto(2) }
      MAX-ACCESS  read-write
      STATUS      current
      DESCRIPTION  "Set or get the 5.0GHz extension channel.The value of extension channel depends on the arrisRouterWiFi50Channel."
      DEFVAL { 2 }
      ::= { arrisRouterWiFi50RadioSettings 37 }

arrisRouterWiFiNumSSIDSupported OBJECT-TYPE
     SYNTAX      Unsigned32
     MAX-ACCESS  read-only
     STATUS      current
     DESCRIPTION "Number of SSIDs Supported"
     ::= { arrisRouterWirelessCfg 51 }

arrisRouterWiFiAllChannelsAllowed OBJECT-TYPE
     SYNTAX      TruthValue
     MAX-ACCESS  read-write
     STATUS      current
     DESCRIPTION "only allow the channel 1,6,11(false) or allow all channels(true) in Auto Mode"
     DEFVAL { true }
     ::= { arrisRouterWirelessCfg 52 }

arrisRouterBssMSOSSID0Setting OBJECT-TYPE
     SYNTAX      INTEGER
     MAX-ACCESS  read-only
     STATUS      current
     DESCRIPTION "The MSO setting to Wi-Fi SSID0 enable/disable"
     DEFVAL  { 1 }
     ::= { arrisRouterWirelessCfg 53 }

arrisrouterWifiClientIdleTimeout OBJECT-TYPE
     SYNTAX      Unsigned32
     UNITS	 "seconds"
     MAX-ACCESS  read-write
     STATUS      current
     DESCRIPTION "The timeout of WiFi clients offline. The configurable value is 60~65536 seconds in MTK's driver."
     ::= { arrisRouterWirelessCfg 54 }

arrisRouterWiFiHTTxStream OBJECT-TYPE
     SYNTAX     Unsigned32 (1..3)
     MAX-ACCESS  read-write
     STATUS      current
     DESCRIPTION  "Set or get the stream number on which the wireless antenna transmits."
     ::= { arrisRouterWirelessCfg 55 }

arrisRouterWiFiHTRxStream OBJECT-TYPE
     SYNTAX     Unsigned32 (1..3)
     MAX-ACCESS  read-write
     STATUS      current
     DESCRIPTION  "Set or get the stream number on which the wireless antenna receives."
     ::= { arrisRouterWirelessCfg 56 }

arrisRouterWiFiEnableSTBC OBJECT-TYPE
     SYNTAX      TruthValue
     MAX-ACCESS  read-write
     STATUS      current
     DESCRIPTION "Enable or disable Space Time Block Coding."
     DEFVAL { false }
     ::= { arrisRouterWirelessCfg 57}

arrisRouterWiFiEnableRDG OBJECT-TYPE
     SYNTAX      TruthValue
     MAX-ACCESS  read-write
     STATUS      current
     DESCRIPTION "Enable or disable Reverse Direction Grant."
     DEFVAL { false }
     ::= { arrisRouterWirelessCfg 58 }

arrisRouterWiFiIGMPSnooping OBJECT-TYPE
     SYNTAX      TruthValue
     MAX-ACCESS  read-write
     STATUS      current
     DESCRIPTION "Enable or disable IGMP snooping.
                  When enabled it prevents unnecessary multicast traffic to the ports which did not subscribe to the multicast stream."
     DEFVAL { false }
     ::= { arrisRouterWirelessCfg 59 }

arrisRouterWiFiRTSRetry OBJECT-TYPE
    SYNTAX      INTEGER (0..255)
    MAX-ACCESS  read-write
    STATUS      current
    DESCRIPTION "Set or get the 2.4GHz RTS retry count. A non-zero value overrides the default RTS retry logic for single-client and multi-client.  If non-zero then the MIB value is the count used for RTS retries. Recommended value is between 1-32."
    DEFVAL {0}
    ::= { arrisRouterWirelessCfg 60 }

arrisRouterWiFiTxRetry OBJECT-TYPE
    SYNTAX      INTEGER (0..255)
    MAX-ACCESS  read-write
    STATUS      current
    DESCRIPTION "Set or get the 2.4GHz Tx retry count.  A non-zero value overrides the default data Tx retry logic for single-client and multi-client.  If non-zero then the MIB value is the count used for data Tx retries. Recommended value is between 1-32."
    DEFVAL {0}
    ::= { arrisRouterWirelessCfg 61 }

-- Radio Statistics Gathering setting and report

arrisRouterWiFiPhysicalChannelStats	OBJECT IDENTIFIER ::= { arrisRouterWirelessCfg 62 }

arrisRouterWiFiPhysicalChannelStatsEnable OBJECT-TYPE
	SYNTAX INTEGER
	{
		disabled(0),
		enable-2-4(1),
		enable-5(2),
		enable-all(3)
	}
	MAX-ACCESS read-write
	STATUS current
	DESCRIPTION
		"Enable collection of the Physical Channel Statistics (per Radio)"
	DEFVAL { 0 }
	::= { arrisRouterWiFiPhysicalChannelStats 1 }

arrisRouterWiFiPhysicalChannelStatsMeasurementRate OBJECT-TYPE
	SYNTAX Integer32 (5..300)
	MAX-ACCESS read-write
	STATUS current
	DESCRIPTION
		"Periodic Measurement Rate for specific measurements (seconds)"
	DEFVAL { 30 }
	::= { arrisRouterWiFiPhysicalChannelStats 2 }

arrisRouterWiFiPhysicalChannelStatsMeasurementInterval OBJECT-TYPE
	SYNTAX Integer32 (300..3600)
	MAX-ACCESS read-write
	STATUS current
	DESCRIPTION
		"Measurement interval for reporting statistics (seconds)"
	DEFVAL { 1800 }
	::= { arrisRouterWiFiPhysicalChannelStats 3 }

arrisRouterChannelStatsMeasurementTable OBJECT-TYPE
	SYNTAX SEQUENCE OF ArrisRouterChannelStatsMeasurementEntry
	MAX-ACCESS not-accessible
	STATUS current
	DESCRIPTION
		"Table contains measurements for individual radio interfaces."
	::= { arrisRouterWiFiPhysicalChannelStats 4 }

arrisRouterChannelStatsMeasurementEntry OBJECT-TYPE
	SYNTAX ArrisRouterChannelStatsMeasurementEntry
	MAX-ACCESS not-accessible
	STATUS current
	DESCRIPTION
		"Table contains measurements for individual radio interfaces."
	INDEX { ifIndex }
	::= { arrisRouterChannelStatsMeasurementTable 1 }

ArrisRouterChannelStatsMeasurementEntry ::= SEQUENCE {
		arrisRouterChannelStatsMinNoiseFloor            Integer32,
		arrisRouterChannelStatsMaxNoiseFloor            Integer32,
		arrisRouterChannelStatsMedianNoiseFloor         Integer32,
		arrisRouterChannelStatsPacketsSent              Counter64,
		arrisRouterChannelStatsPacketsReceived          Counter64,
		arrisRouterChannelStatsCSTExceedPercent         Integer32,
		arrisRouterChannelStatsActivityFactor           Integer32,
		arrisRouterChannelStatsChannelUtilization       Integer32,
		arrisRouterChannelStatsRetransmissionsMetric	Integer32
	}

arrisRouterChannelStatsMinNoiseFloor OBJECT-TYPE
	SYNTAX Integer32
	MAX-ACCESS read-only
	STATUS current
	DESCRIPTION
		"The minimum noise floor (dBm) on the serving channel
		across the measurement interval."
	DEFVAL {-1}
	::= { arrisRouterChannelStatsMeasurementEntry 1 }

arrisRouterChannelStatsMaxNoiseFloor OBJECT-TYPE
	SYNTAX Integer32
	MAX-ACCESS read-only
	STATUS current
	DESCRIPTION
		"The maximum noise floor(dBm) on the serving channel across
		the measurement interval."
	DEFVAL {-1}
	::= { arrisRouterChannelStatsMeasurementEntry 2 }

arrisRouterChannelStatsMedianNoiseFloor OBJECT-TYPE
	SYNTAX Integer32
	MAX-ACCESS read-only
	STATUS current
	DESCRIPTION
		"The median noise floor (dBm) on the serving channel across
		the measurement interval."
	DEFVAL {-1}
	::= { arrisRouterChannelStatsMeasurementEntry 3 }

arrisRouterChannelStatsPacketsSent OBJECT-TYPE
	SYNTAX Counter64
	MAX-ACCESS read-only
	STATUS current
	DESCRIPTION
                "Total number of packets transmitted out of the radio
                across the measurement interval."
	DEFVAL {0}
	::= { arrisRouterChannelStatsMeasurementEntry 4 }

arrisRouterChannelStatsPacketsReceived OBJECT-TYPE
	SYNTAX Counter64
	MAX-ACCESS read-only
	STATUS current
	DESCRIPTION
		"Total number of packets received on the radio across the
		measurement interval."
	DEFVAL {0}
	::= { arrisRouterChannelStatsMeasurementEntry 5 }

arrisRouterChannelStatsCSTExceedPercent OBJECT-TYPE
	SYNTAX Integer32
	MAX-ACCESS read-only
	STATUS current
	DESCRIPTION
		"Percentage of time the CST was exceeded across the radio
		across the measurement interval."
	DEFVAL {-1}
	::= { arrisRouterChannelStatsMeasurementEntry 6 }

arrisRouterChannelStatsActivityFactor OBJECT-TYPE
	SYNTAX Integer32
	MAX-ACCESS read-only
	STATUS current
	DESCRIPTION
		"Percentage of air time the radio was actively utilizing
		the channel across the measurement interval."
	DEFVAL {-1}
	::= { arrisRouterChannelStatsMeasurementEntry 7 }

arrisRouterChannelStatsChannelUtilization OBJECT-TYPE
	SYNTAX Integer32
	MAX-ACCESS read-only
	STATUS current
	DESCRIPTION
		"Percentage of time the medium was utilized on the channel
		across the measurement interval"
	DEFVAL {-1}
	::= { arrisRouterChannelStatsMeasurementEntry 8 }

arrisRouterChannelStatsRetransmissionsMetric OBJECT-TYPE
	SYNTAX Integer32
	MAX-ACCESS read-only
	STATUS current
	DESCRIPTION
		"Percentage of packets that had to be retransmitted the
		measurement interval"
	DEFVAL {-1}
	::= { arrisRouterChannelStatsMeasurementEntry 9 }

arrisRouterChannelStatsRSSITable OBJECT-TYPE
	SYNTAX SEQUENCE OF ArrisRouterChannelStatsRSSITableEntry
	MAX-ACCESS not-accessible
	STATUS current
	DESCRIPTION
		"Table contains a histogram of client RSSI Values across
		the measurement interval."
	::= { arrisRouterWiFiPhysicalChannelStats 5 }

arrisRouterChannelStatsRSSITableEntry OBJECT-TYPE
	SYNTAX ArrisRouterChannelStatsRSSITableEntry
	MAX-ACCESS not-accessible
	STATUS current
	DESCRIPTION
		""
	INDEX { ifIndex, arrisRouterChannelStatsRSSITableIndex }
	::= { arrisRouterChannelStatsRSSITable 1 }

ArrisRouterChannelStatsRSSITableEntry ::= SEQUENCE {
	    arrisRouterChannelStatsRSSITableIndex	Integer32,
	    arrisRouterChannelStatsRSSICount	    	Integer32
	}

arrisRouterChannelStatsRSSITableIndex OBJECT-TYPE
     SYNTAX      Integer32 (1..40)
     MAX-ACCESS  not-accessible
     STATUS      current
     DESCRIPTION
         "Index used to order the ChannelStatsRSSITable entries."
     ::= { arrisRouterChannelStatsRSSITableEntry 1 }

arrisRouterChannelStatsRSSICount OBJECT-TYPE
     SYNTAX      Integer32
     MAX-ACCESS  read-only
     STATUS      current
     DESCRIPTION
         "The RSSI Count for this 'bin'."
     DEFVAL { -1 }
     ::= { arrisRouterChannelStatsRSSITableEntry 2 }

arrisRouterWiFiPhysicalChannelStatisticsStartTime OBJECT-TYPE
     SYNTAX          DisplayString (SIZE (0..64))
     MAX-ACCESS      read-only
     STATUS          current
     DESCRIPTION
         "Channel Statistics start time"
     DEFVAL { "Unknown Time" }
     ::= { arrisRouterWiFiPhysicalChannelStats 6 }

arrisRouterWiFiPhysicalChannelStats5GEnable OBJECT-TYPE
     SYNTAX       TruthValue
     MAX-ACCESS   read-write
     STATUS       current
     DESCRIPTION  "Enable collection of the Physical Channel Statistics (5GHz Radio)"
     DEFVAL { false }
     ::= { arrisRouterWiFiPhysicalChannelStats 7 }

-- OIDs for 5 Ghz radio for wmm and wps
arrisRouterWMM50Cfg			 OBJECT IDENTIFIER ::= { arrisRouterWirelessCfg 63}

arrisRouterWMM50Enable OBJECT-TYPE
    SYNTAX      TruthValue
    MAX-ACCESS  read-write
    STATUS      current
    DESCRIPTION "Enable/disable WiFi MultiMedia (WMM) QOS support.. Note that this applies to only the primary (zero) Wireless network."
    DEFVAL { true }
    ::= { arrisRouterWMM50Cfg 1 }

arrisRouterWMM50NoAck OBJECT-TYPE
    SYNTAX      TruthValue
    MAX-ACCESS  read-write
    STATUS      current
    DESCRIPTION "This refers to the acknowledge policy used at the MAC level.
				Enabling no-acknowledgement can result in more efficient throughput but
				higher error rates in a noisy Radio Frequency (RF) environment."
	DEFVAL { false }
    ::= { arrisRouterWMM50Cfg 2 }

arrisRouterWMM50APSD OBJECT-TYPE
    SYNTAX      TruthValue
    MAX-ACCESS  read-write
    STATUS      current
    DESCRIPTION "Automatic Power Save Delivery is a more efficient power management method than legacy 802.11 Power Save Polling.
				Set the value here."
	DEFVAL { true }
    ::= { arrisRouterWMM50Cfg 3 }

arrisRouterWMM50EDCAAPTable  OBJECT-TYPE
    SYNTAX      SEQUENCE OF ArrisRouterWMM50EDCAAPEntry
    MAX-ACCESS  not-accessible
    STATUS      current
    DESCRIPTION "A table of for setting WMM EDCA values for the access point.
				This affects traffic flowing from the access point to the client station "
    ::= { arrisRouterWMM50Cfg 4 }

arrisRouterWMM50EDCAAPEntry OBJECT-TYPE
    SYNTAX      ArrisRouterWMM50EDCAAPEntry
    MAX-ACCESS  not-accessible
    STATUS      current
    DESCRIPTION "A table of for setting WMM EDCA values for the access point.
				This affects traffic flowing from the access point to the client station "
    INDEX   { arrisRouterWMM50EDCAAPIndex }
    ::= { arrisRouterWMM50EDCAAPTable 1 }

ArrisRouterWMM50EDCAAPEntry ::=
    SEQUENCE    {
                arrisRouterWMM50EDCAAPIndex			Integer32,
                arrisRouterWMM50EDCAAPCWmin			Unsigned32,
                arrisRouterWMM50EDCAAPCWmax			Unsigned32,
                arrisRouterWMM50EDCAAPAIFSN			Unsigned32,
                arrisRouterWMM50EDCAAPTxOpBLimit		Unsigned32,
                arrisRouterWMM50EDCAAPTxOpAGLimit		Unsigned32,
                arrisRouterWMM50EDCAAPAdmitCont                 TruthValue,
                arrisRouterWMM50EDCAAPDiscardOld		TruthValue
    }

arrisRouterWMM50EDCAAPIndex OBJECT-TYPE
    SYNTAX      Integer32 (1..4)
    MAX-ACCESS  not-accessible
    STATUS      current
    DESCRIPTION "The index into the table will be one of the parameters: 1=ACBE (best effort), 2=ACBK (background), 3=ACVI (video), 4=ACVO (voice)"
    ::= { arrisRouterWMM50EDCAAPEntry 1 }

arrisRouterWMM50EDCAAPCWmin OBJECT-TYPE
    SYNTAX      Unsigned32
    UNITS		"milliseconds"
    MAX-ACCESS  read-write
    STATUS      current
	DESCRIPTION "Minimum Contention Window.
				 This parameter is input to the algorithm that determines the initial random backoff wait time (window) for retry of a transmission.
				 The value specified here in the Minimum Contention Window is the upper limit of a range from which the initial random backoff
				 wait time is determined. The first random number generated will be a number between 0 and the number specified here.
				 If the first random backoff wait time expires before the data frame is sent, a retry counter is incremented and the
				 random backoff value (window) is doubled. Doubling will continue until the size of the random backoff value reaches the number
				 defined in the Maximum Contention Window.
				 Valid values are 1, 3, 7, 15, 31, 63, 127, 255, and 511.
				 This value must be lower than the value for arrisRouterWMMEDCAAPCWmax"
    ::= { arrisRouterWMM50EDCAAPEntry 2 }

arrisRouterWMM50EDCAAPCWmax OBJECT-TYPE
    SYNTAX      Unsigned32
    UNITS		"milliseconds"
    MAX-ACCESS  read-write
    STATUS      current
    DESCRIPTION "Maximum Contention Window. The value specified here in the Maximum Contention Window is the upper limit for the
				 doubling of the random backoff value. This doubling continues until either the data frame is sent or the
				 Maximum Contention Window size is reached. Once the Maximum Contention Window size is reached, retries
				 will continue until a maximum number of retries allowed is reached.
				 Valid values are 1, 3, 7, 15, 31, 63, 127, 255, 511, and 1023.
				 This value must be higher than the value for arrisRouterWMMEDCAAPCWmin."
    ::= { arrisRouterWMM50EDCAAPEntry 3 }

arrisRouterWMM50EDCAAPAIFSN OBJECT-TYPE
    SYNTAX      Unsigned32
    UNITS		"milliseconds"
    MAX-ACCESS  read-write
    STATUS      current
    DESCRIPTION "The Arbitration Inter-Frame Spacing Number specifies a wait time for data frames"
    ::= { arrisRouterWMM50EDCAAPEntry 4 }

arrisRouterWMM50EDCAAPTxOpBLimit OBJECT-TYPE
    SYNTAX      Unsigned32 (0..65535)
    UNITS		"microseconds"
    MAX-ACCESS  read-write
    STATUS      current
    DESCRIPTION "Transmission Opportunity for b mode is an interval of time when a WME AP has the right to initiate
				transmissions onto the wireless medium (WM). This value specifies the Transmission Opportunity (TXOP) for AP;
				that is, the interval of time when the WMM AP has the right to initiate transmissions on the wireless network."
    ::= { arrisRouterWMM50EDCAAPEntry 5 }

arrisRouterWMM50EDCAAPTxOpAGLimit OBJECT-TYPE
    SYNTAX      Unsigned32 (0..65535)
    UNITS		"microseconds"
    MAX-ACCESS  read-write
    STATUS      current
    DESCRIPTION "Transmission Opportunity for A and G mode is an interval of time when a WME AP has the right to initiate
				transmissions onto the wireless medium (WM). This value specifies the Transmission Opportunity (TXOP) for AP;
				that is, the interval of time when the WMM AP has the right to initiate transmissions on the wireless network."
    ::= { arrisRouterWMM50EDCAAPEntry 6 }

arrisRouterWMM50EDCAAPAdmitCont OBJECT-TYPE
    SYNTAX      TruthValue
    MAX-ACCESS  read-write
    STATUS      current
    DESCRIPTION "Enable/disable admission control for specific category of traffic."
    ::= { arrisRouterWMM50EDCAAPEntry 7 }

arrisRouterWMM50EDCAAPDiscardOld OBJECT-TYPE
    SYNTAX      TruthValue
    MAX-ACCESS  read-write
    STATUS      current
    DESCRIPTION "Discard oldest packet first enable/disable."
    ::= { arrisRouterWMM50EDCAAPEntry 8 }

arrisRouterWiFiExtensionChannel OBJECT-TYPE
     SYNTAX     INTEGER { belowControlChannel(0), aboveControlChannel(1), auto(2) }
     MAX-ACCESS  read-write
     STATUS      current
     DESCRIPTION  "Set or get the 2.4GHz extension channel for 40MHz operation
                   The value of extension channel depends on the arrisRouterWiFiChannel."
     ::= { arrisRouterWirelessCfg 64 }

arrisRouterWPS50Cfg			 OBJECT IDENTIFIER ::= { arrisRouterWirelessCfg 65 }

arrisRouterWps50Mode OBJECT-TYPE
    SYNTAX      INTEGER { disabled(0), enabled(1) }
    MAX-ACCESS  read-write
    STATUS      current
    DESCRIPTION "Get and set whether or not WiFi Protected Setup (WPS) is enabled or disabled.
                 The WPS mode can't be set to enabled(1) when the primary SSID arrisRouterBssSecurityMode is wep(1)."
    ::= { arrisRouterWPS50Cfg 1 }

arrisRouterWps50ConfigState OBJECT-TYPE
    SYNTAX      INTEGER { disabled(0), enabled(1) }
    MAX-ACCESS  read-write
    STATUS      current
    DESCRIPTION "Get and set the WiFi Protected Setup (WPS) config state."
    ::= { arrisRouterWPS50Cfg 2 }

arrisRouterWps50DevicePIN OBJECT-TYPE
    SYNTAX      DisplayString (SIZE(8))
    MAX-ACCESS  read-write
    STATUS      current
    DESCRIPTION "Get or set the WiFi Protected Setup (WPS) device PIN.  This is the PIN that is displayed to the user to input on their client device."
    ::= { arrisRouterWPS50Cfg 3 }

arrisRouterWps50DeviceName OBJECT-TYPE
    SYNTAX      DisplayString (SIZE(0..32))
    MAX-ACCESS  read-only
    STATUS      current
    DESCRIPTION "Name of this device"
    ::= { arrisRouterWPS50Cfg 4 }

arrisRouterWps50ModelName OBJECT-TYPE
    SYNTAX      DisplayString (SIZE(0..32))
    MAX-ACCESS  read-only
    STATUS      current
    DESCRIPTION "Model Name"
    ::= { arrisRouterWPS50Cfg 5 }

arrisRouterWps50Mfg OBJECT-TYPE
    SYNTAX      DisplayString (SIZE(0..64))
    MAX-ACCESS  read-write
    STATUS      current
    DESCRIPTION "Manufacturer string"
    ::= { arrisRouterWPS50Cfg 6 }

arrisRouterWps50ResultStatus OBJECT-TYPE
    SYNTAX      INTEGER {
			wpsResultUnknown(-1),
			wpsResultNoneIssued(0),
			wpsResultAddClientSuccess(1),
			wpsResultAddClientFail(2),
			wpsResultAddClientAbort(3),
			wpsResultConfigApSuccess(4),
			wpsResultConfigApFail(5),
			wpsResultConfigApAbort(6),
			wpsResultOverlap(7),
			wpsResultTimedOut(8),
			wpsResultInProgress(9)
			}
    MAX-ACCESS  read-only
    STATUS      current
    DESCRIPTION  "The result status of the most recent WPS operation."
	::= { arrisRouterWPS50Cfg 7 }


arrisRouterWps50Status OBJECT-TYPE
    SYNTAX      INTEGER {
			wpsUnknown(-1),
			wpsInitialState(0),
			wpsAssociatedStarted(1),
			wpsM2Sent(2),
			wpsM7Sent(3),
			wpsTimedOut(4),
			wpsMsgDone(5),
			wpsSuccessful(6),
			wpsMsgExchangeErr(7),
			wpsPushButtonOverlap(8),
			wpsAssociating(9),
			wpsPushButtonFindAP(10)
			}
    MAX-ACCESS  read-only
    STATUS      current
    DESCRIPTION  "Current status of the WPS subsystem."
	::= { arrisRouterWPS50Cfg 8 }

arrisRouterWps50ConfigTimeout OBJECT-TYPE
    SYNTAX      INTEGER { disabled(0), enabled(1) }
    MAX-ACCESS  read-write
    STATUS      current
    DESCRIPTION "Get and set whether the WiFi Protected Setup (WPS) uses timeout."
    ::= { arrisRouterWPS50Cfg 9 }

arrisRouterWps50STAPin OBJECT-TYPE
    SYNTAX      DisplayString (SIZE(8))
    MAX-ACCESS  read-write
    STATUS      current
    DESCRIPTION "Set the WiFi Protected Setup (WPS) PIN for a new station/device.  This is the PIN from a 'client' device."
    ::= { arrisRouterWPS50Cfg 10 }

arrisRouterWps50PushButton OBJECT-TYPE
    SYNTAX      INTEGER { unknown(0), activatePushButton(1), activatePINCfg(2), cancelWPS(3) }
    MAX-ACCESS  read-write
    STATUS      current
    DESCRIPTION "Set to 'activatePushButton' to push the virtual button on the Access Point and start the WPS push-button process.
				Set to 'activePINCfg' to start the WPS PIN process.  The client device PIN should be written to arrisRouterWps50STAPin
				before triggering the WPS process.
				Cancel an active WPS config (started with either 1 or 2) by setting this value to 'cancelWPS'."
    ::= { arrisRouterWPS50Cfg 11 }


arrisRouterWps50UUID OBJECT-TYPE
    SYNTAX      DisplayString (SIZE(0..16))
    MAX-ACCESS  read-write
    STATUS      current
    DESCRIPTION  "Sets WPS Universal Unique Identifier"
	::= { arrisRouterWPS50Cfg 14 }

arrisRouterWPS50MethodCfg OBJECT IDENTIFIER ::= { arrisRouterWPS50Cfg 15 }

arrisRouterWPS50MethodLabel OBJECT-TYPE
    SYNTAX      INTEGER { disabled(0), enabled(1) }
    MAX-ACCESS  read-write
    STATUS      current
    DESCRIPTION "Get and set whether or not WPS Label Method is enabled or disabled."
    ::= { arrisRouterWPS50MethodCfg 1 }

arrisRouterWPS50MethodPIN OBJECT-TYPE
    SYNTAX      INTEGER { disabled(0), enabled(1) }
    MAX-ACCESS  read-write
    STATUS      current
    DESCRIPTION "Get and set whether or not WPS PIN Method is enabled or disabled."
    ::= { arrisRouterWPS50MethodCfg 2 }

arrisRouterWPS50MethodPushButton OBJECT-TYPE
    SYNTAX      INTEGER { disabled(0), enabled(1) }
    MAX-ACCESS  read-write
    STATUS      current
    DESCRIPTION "Get and set whether or not WPS Push Button Method is enabled or disabled."
    ::= { arrisRouterWPS50MethodCfg 3 }

arrisRouterWPS50MethodKeypad OBJECT-TYPE
    SYNTAX      INTEGER { disabled(0), enabled(1) }
    MAX-ACCESS  read-write
    STATUS      current
    DESCRIPTION "Get and set whether or not WPS Keypad Method is enabled or disabled."
    ::= { arrisRouterWPS50MethodCfg 4 }

arrisRouterWps50LockDownStatus OBJECT-TYPE
    SYNTAX      TruthValue
    MAX-ACCESS  read-write
    STATUS      current
    DESCRIPTION "Indicates the WPS Lockdown state, returns true when WPS is in lock state caused by incorrect number of PIN entries, set to false to release
                 WPS lockdown state."
    DEFVAL     { false }
    ::= { arrisRouterWPS50Cfg 16 }

arrisRouterWifiLowInitRate OBJECT-TYPE
	 SYNTAX      TruthValue
	 MAX-ACCESS  read-write
	 STATUS      current
	 DESCRIPTION "Set true will reduce data rate based on increasing packet error ratio. Set false will turn off this function."
	 DEFVAL { false }
	 ::= { arrisRouterWirelessCfg 66 }

arrisRouterBandSteering OBJECT IDENTIFIER ::= { arrisRouterWirelessCfg 67}

arrisRouterOperationalBandSteerEnable OBJECT-TYPE
    SYNTAX TruthValue
    MAX-ACCESS read-write
    STATUS current
    DESCRIPTION
        "Enable Operational Band Steering -- (Client is Associated)"
    DEFVAL { false }
    ::= { arrisRouterBandSteering 2 }

arrisRouterBandSteeringCfg OBJECT IDENTIFIER ::= { arrisRouterBandSteering 5 }

arrisRouterBandSteer2gRssiLowLimit OBJECT-TYPE
    SYNTAX INTEGER
    MAX-ACCESS read-write
    STATUS current
    DESCRIPTION
    	"2.4 GHz RSSI (dBm) Low Threshold.
    	Threshold for which 2.4 GHz signal is considered too weak."
    DEFVAL { -75 }
    ::= { arrisRouterBandSteeringCfg 1 }

arrisRouterBandSteer5gRssiGoodLimit OBJECT-TYPE
    SYNTAX INTEGER
    MAX-ACCESS read-write
    STATUS current
    DESCRIPTION
    	"5 GHz RSSI (dBm) Good Threshold.
    	Threshold for which 5 GHz signal is considered good."
    DEFVAL { -60 }
    ::= { arrisRouterBandSteeringCfg 2  }

arrisRouterBandSteerAssocLowRssiThreshold OBJECT-TYPE
    SYNTAX INTEGER
    MAX-ACCESS read-write
    STATUS current
    DESCRIPTION
        "RSSI (dBm) threshold on Target Band where signal strength
        is too low for association"
    DEFVAL { -75 }
    ::= { arrisRouterBandSteeringCfg 6 }

arrisRouterBandSteerInactiveTime2Overload OBJECT-TYPE
    SYNTAX INTEGER
    MAX-ACCESS read-write
    STATUS current
    DESCRIPTION
        "Client Inactivity Time (seconds) on overloaded 2G Band before
        directing client to 5 GHz."
    DEFVAL { 30 }
    ::= { arrisRouterBandSteeringCfg 7 }

arrisRouterBandSteerInactiveTime2Normal OBJECT-TYPE
    SYNTAX INTEGER
    MAX-ACCESS read-write
    STATUS current
    DESCRIPTION
        "Client Inactivity Time (seconds) on normal 2G Band before
        directing client to 5 GHz based on other conditions."
    DEFVAL { 300 }
    ::= { arrisRouterBandSteeringCfg 8 }

arrisRouterBandSteerInactiveTime5Overload OBJECT-TYPE
    SYNTAX INTEGER
    MAX-ACCESS read-write
    STATUS current
    DESCRIPTION
        "Client Inactivity Time (seconds) on overloaded 5G Band before
        directing client to 2 GHz."
    DEFVAL { 30 }
    ::= { arrisRouterBandSteeringCfg 9 }

arrisRouterBandSteerInactiveTime5Normal OBJECT-TYPE
    SYNTAX INTEGER
    MAX-ACCESS read-write
    STATUS current
    DESCRIPTION
        "Client Inactivity Time (seconds) on normal 5G Band before
        directing client to 2 GHz based on other conditions."
    DEFVAL { 150 }
    ::= { arrisRouterBandSteeringCfg 10 }

arrisRouterBandSteerProhibitTime OBJECT-TYPE
    SYNTAX INTEGER
    MAX-ACCESS read-write
    STATUS current
    DESCRIPTION
        "Time Period (seconds) to wait prior to steering a client after
        a previous steer."
    DEFVAL { 300 }
    ::= { arrisRouterBandSteeringCfg 12 }

arrisRouterBandSteerUtilSamplePeriod OBJECT-TYPE
    SYNTAX INTEGER
    MAX-ACCESS read-write
    STATUS current
    DESCRIPTION
        "Time Period (seconds) to gather instantaneous channel utilization data."
    DEFVAL { 10 }
    ::= { arrisRouterBandSteeringCfg 13 }

arrisRouterBandSteerUtilAvgPeriod OBJECT-TYPE
    SYNTAX INTEGER
    MAX-ACCESS read-write
    STATUS current
    DESCRIPTION
        "Time Period (seconds) to average the instaneous channel utilization data."
    DEFVAL { 300 }
    ::= { arrisRouterBandSteeringCfg 14 }

arrisRouterBandSteerClientSteeringTime OBJECT-TYPE
    SYNTAX INTEGER
    MAX-ACCESS read-write
    STATUS current
    DESCRIPTION
        "Time Period (seconds) Maximum Time allowed for the client to reconnect before
        aborting client steering and releasing the client from the blacklist."
    DEFVAL { 15 }
    ::= { arrisRouterBandSteeringCfg 15 }

arrisRouterBandSteerClientSteerCount OBJECT-TYPE
    SYNTAX INTEGER
    MAX-ACCESS read-write
    STATUS current
    DESCRIPTION
        "Maximum Consecutive client authentication rejects before aborting client steering
        and releasing the client from the respective blacklist.  A value of zero (0) indicates
        Client Steering Count is disabled."
    DEFVAL { 3 }
    ::= { arrisRouterBandSteeringCfg 16 }

arrisRouterBandSteer2gLoadLimit OBJECT-TYPE
    SYNTAX INTEGER
    MAX-ACCESS read-write
    STATUS current
    DESCRIPTION
       "2 GHz Load Limit (percentage).
        Threshold for which 2 GHz signal is considered overloaded."
    DEFVAL { 70 }
    ::= { arrisRouterBandSteeringCfg 17 }

arrisRouterBandSteer5gLoadLimit OBJECT-TYPE
    SYNTAX INTEGER
    MAX-ACCESS read-write
    STATUS current
    DESCRIPTION
       "5 GHz Load Limit (percentage).
        Threshold for which 5 GHz signal is considered overloaded."
    DEFVAL { 70 }
    ::= { arrisRouterBandSteeringCfg 18 }

arrisRouterBandSteerHoldTime OBJECT-TYPE
	SYNTAX INTEGER (0..300)
	MAX-ACCESS read-write
	STATUS current
	DESCRIPTION
    "Time for holding the 2.4GHz connection responses, If there is no connection request
    from dual band client on 5G within HoldTime , then AP will consider the client does
    not want to connect to 5GHz and connection on 2.4GHz will be allowed.
    Note that only MTK DBC solution support this MIB"
    DEFVAL { 90 }
    ::= { arrisRouterBandSteeringCfg 19 }

arrisRouterBandSteerRssiDiff OBJECT-TYPE
	SYNTAX INTEGER (0..100)
	MAX-ACCESS read-write
	STATUS current
	DESCRIPTION
    "If RSSI of 2.4GHz is greater than RSSI of 5GHz by RssiDiff then allow client to connect
    2.4G immediately.
    Note that only MTK DBC solution support this MIB"
    DEFVAL { 30 }
    ::= { arrisRouterBandSteeringCfg 20 }

arrisRouterBandSteerRssiLow OBJECT-TYPE
	SYNTAX INTEGER (-100..0)
	MAX-ACCESS read-write
	STATUS current
	DESCRIPTION
    "If a dual band station's RSSI of 5GHz is less than RssiLow then this station is not
    allowed to connect 5G. A dual band STA connected to 5G will be kicked out if it's RSSI
    goes below 10dbm from RssiLow.
    Note that only MTK DBC solution support this MIB"
    DEFVAL { -70 }
    ::= { arrisRouterBandSteeringCfg 21 }

arrisRouterBandSteerAgeOutTime OBJECT-TYPE
	SYNTAX INTEGER (0..3600)
	MAX-ACCESS read-write
	STATUS current
	DESCRIPTION
    "Age out time after when a STA is inserted into the Band Steering table. STA will be
    removed from the table when the above time will expire and will be reinserted after
    receiving Prob/Auth frame from the STA.
    Note that only MTK DBC solution support this MIB"
    DEFVAL { 150 }
    ::= { arrisRouterBandSteeringCfg 22 }

arrisRouterBandSteerCheckTime OBJECT-TYPE
	SYNTAX INTEGER (0..300)
	MAX-ACCESS read-write
	STATUS current
	DESCRIPTION
    "After receiving a 2.4GHz prob/auth request, if no 5GHz probe/auth request received by
    AP within check time, the AP will consider the STA is a 2.4GHz only STA.
    Note that only MTK DBC solution support this MIB"
    DEFVAL { 30 }
    ::= { arrisRouterBandSteeringCfg 23 }

arrisRouterBandSteerCndChk OBJECT-TYPE
     SYNTAX      Unsigned32
     MAX-ACCESS  read-write
     STATUS      current
     DESCRIPTION "Which condition be used by band steering. Multiple conditions can be set by using the binary OR of the values.
                  This mib object takes in an unsigned integer with the
                  following bitmap setup:

                  0x00000001 // check RSSI Diff
                  0x00000002 // check 2GHz Persist (Client really don't want to connect 5GHz)
                  0x00000004 // check HT support
                  0x00000008 // check 5GHz RSSI

                  Note that only MTK DBC solution support this MIB"
    ::= { arrisRouterBandSteeringCfg 24 }

arrisRouterWiFiBssStaSteering OBJECT IDENTIFIER ::= { arrisRouterWirelessCfg 69}

arrisRouterWiFiBssStaSteeringReset OBJECT-TYPE
    SYNTAX          TruthValue
    MAX-ACCESS      read-write
    STATUS          current
    DESCRIPTION        "Remove all STA Steering Lists (Global) and reset Groups to defaults."
    DEFVAL { false }
    ::= { arrisRouterWiFiBssStaSteering 1 }

arrisRouterWiFiBssStaSteeringDenyCount OBJECT-TYPE
    SYNTAX          INTEGER (1..10)
    MAX-ACCESS      read-write
    STATUS          current
    DESCRIPTION        "Number of Association tries before allowing a STA
                     to join a blocked BSS (Global config for all lists)."
    DEFVAL { 5 }
    ::= { arrisRouterWiFiBssStaSteering 2 }

arrisRouterWiFiBssStaSteeringDenyWindow OBJECT-TYPE
    SYNTAX          INTEGER (0..120)
    MAX-ACCESS      read-write
    STATUS          current
    DESCRIPTION        "Number of Seconds before Deny Count is reset (Global config for all lists).
                    0 = Deny Window is disabled"
    DEFVAL { 0 }
    ::= { arrisRouterWiFiBssStaSteering 3 }

-- Provide Configuration for Per BSS STA Steering

arrisRouterBssStaSteeringTable OBJECT-TYPE
      SYNTAX      SEQUENCE OF ArrisRouterBssStaSteeringEntry
      MAX-ACCESS  not-accessible
      STATUS      current
      DESCRIPTION "Table containing BSS Steering Entries indexed by ifIndex."
      ::= { arrisRouterWiFiBssStaSteering 4 }

arrisRouterBssStaSteeringEntry OBJECT-TYPE
      SYNTAX      ArrisRouterBssStaSteeringEntry
      MAX-ACCESS  not-accessible
      STATUS      current
      DESCRIPTION "Table containing STA Steering BSS Group entries."
      INDEX { ifIndex }
      ::= { arrisRouterBssStaSteeringTable 1 }

ArrisRouterBssStaSteeringEntry ::= SEQUENCE {
        arrisRouterBssStaSteeringIndex            Integer32,
        arrisRouterBssStaSteeringTableClear       Integer32,
        arrisRouterBssStaSteeringTableDenyCount   Integer32,
        arrisRouterBssStaSteeringTableDenyWindow  Integer32,
        arrisRouterBssStaSteeringTableStatus      RowStatus
        }

arrisRouterBssStaSteeringIndex OBJECT-TYPE
   SYNTAX      Integer32 (1..16)
   MAX-ACCESS  not-accessible
   STATUS      current
   DESCRIPTION "Table index"
   ::= { arrisRouterBssStaSteeringEntry 1  }

arrisRouterBssStaSteeringTableClear OBJECT-TYPE
    SYNTAX          Integer32 (0..2)
    MAX-ACCESS      read-write
    STATUS          current
    DESCRIPTION        "0 - No Action
                     1 - Reset Table to defaults
                     2 - Clear ifIndex Client List"
    DEFVAL { 0 }
    ::= { arrisRouterBssStaSteeringEntry 2 }

arrisRouterBssStaSteeringTableDenyCount OBJECT-TYPE
    SYNTAX          Integer32 (0..10)
    MAX-ACCESS      read-create
    STATUS          current
    DESCRIPTION        "Number of Association tries before allowing a STA
                     to join another BSS (Local config for this list)."
    DEFVAL { 5 }
    ::= { arrisRouterBssStaSteeringEntry 3 }

arrisRouterBssStaSteeringTableDenyWindow OBJECT-TYPE
    SYNTAX          Integer32 (0..120)
    MAX-ACCESS      read-create
    STATUS          current
    DESCRIPTION        "Number of Seconds before Deny Count is reset (local config for list).
                    0 = Deny Window is disabled"
    DEFVAL { 0 }
    ::= { arrisRouterBssStaSteeringEntry 4 }

arrisRouterBssStaSteeringTableStatus OBJECT-TYPE
    SYNTAX      RowStatus
    MAX-ACCESS  read-create
    STATUS      current
    DESCRIPTION
        "The status of this conceptual row.
         To create a row in this table, a manager must set this object to
         either createAndGo(4) or createAndWait(5).
         Until instances of all corresponding columns are appropriately
         configured, the value of the corresponding instance of the
         arrisRouterBssStaSteeringTableStatus column is 'notReady'.
         Only rows with a status of active(1) will be applied."
    ::= { arrisRouterBssStaSteeringEntry 5 }

-- Client Entries for a BSS Group --------------------------------------

arrisRouterBssStaSteeringClientTable OBJECT-TYPE
    SYNTAX      SEQUENCE OF ArrisRouterBssStaSteeringClientEntry
    MAX-ACCESS  not-accessible
    STATUS      current
    DESCRIPTION " Station Entries Applied to the BSS Group"
    ::= { arrisRouterWiFiBssStaSteering 5 }

arrisRouterBssStaSteeringClientEntry OBJECT-TYPE
    SYNTAX      ArrisRouterBssStaSteeringClientEntry
    MAX-ACCESS  not-accessible
    STATUS      current
    DESCRIPTION " Station Entries for the BSS Group "
    INDEX { ifIndex,
            arrisRouterBssStaSteeringClientIndex  }
    ::= { arrisRouterBssStaSteeringClientTable 1 }

ArrisRouterBssStaSteeringClientEntry ::= SEQUENCE {
        arrisRouterBssStaSteeringClientIndex                  Integer32,
        arrisRouterBssStaSteeringClientMacAddress             MacAddress,
        arrisRouterBssStaSteeringClientLastAssocTime          DateAndTime,
        arrisRouterBssStaSteeringClientOtherBssJoinedCount    Integer32
        }

arrisRouterBssStaSteeringClientIndex OBJECT-TYPE
    SYNTAX      Integer32 (1..64)
    MAX-ACCESS  not-accessible
    STATUS      current
    DESCRIPTION "Table index"
    ::= { arrisRouterBssStaSteeringClientEntry 1  }

arrisRouterBssStaSteeringClientMacAddress OBJECT-TYPE
    SYNTAX      MacAddress
    MAX-ACCESS  read-only
    STATUS      current
    DESCRIPTION "A MAC address of a station which has joined the BSS and should be steered to this BSS."
    ::= { arrisRouterBssStaSteeringClientEntry 2  }

arrisRouterBssStaSteeringClientLastAssocTime OBJECT-TYPE
    SYNTAX      DateAndTime
    MAX-ACCESS  read-only
    STATUS      current
    DESCRIPTION "The date and time when this Client Last Associated."
    ::= { arrisRouterBssStaSteeringClientEntry 3  }

arrisRouterBssStaSteeringClientOtherBssJoinedCount OBJECT-TYPE
    SYNTAX      Integer32
    MAX-ACCESS  read-only
    STATUS      current
    DESCRIPTION "Number of Times the Client was allowed to join another BSS"
    ::= { arrisRouterBssStaSteeringClientEntry 4  }

arrisRouterWiFiInterworkingIE OBJECT-TYPE
    SYNTAX          TruthValue
    MAX-ACCESS      read-write
    STATUS          current
    DESCRIPTION        "Enable or Disable the Interworking Informational
                      Element for ALL BSSs on all radios."
    DEFVAL { true }
    ::= { arrisRouterWirelessCfg 70}

arrisRouterAdvancedRadiusCfg OBJECT IDENTIFIER ::= { arrisRouterWirelessCfg 73 }

arrisRouterAdvancedRadiusCfgSettingsTable OBJECT-TYPE
	SYNTAX		SEQUENCE OF ArrisRouterAdvancedRadiusCfgSettingsEntry
	MAX-ACCESS 	not-accessible
	STATUS		current
	DESCRIPTION

	"This table assigns Advanced Radius Settings to be applied to Radius Servers per BSS.
	An entry exists in this table for each row in the arrisRouterBSSTable
	for which arrisRouterWiFiSecurityMode is set to wpaEnterprise(4),
	wpa2Enterprise(5), or radiusWep(6) when arrisRouterAdvancedRadiusCfg is enabled AND
	arrisRouterAdvancedRadiusCfg_SettingsEnable is true."

	::= { arrisRouterAdvancedRadiusCfg 11 }

arrisRouterAdvancedRadiusCfgSettingsEntry OBJECT-TYPE
	SYNTAX		ArrisRouterAdvancedRadiusCfgSettingsEntry
	MAX-ACCESS      not-accessible
	STATUS		current
	DESCRIPTION

	"This table assigns Advanced Radius Settings to be applied to Radius Servers per BSS.
	An entry exists in this table for each row in the arrisRouterBSSTable
	for which arrisRouterWiFiSecurityMode is set to wpaEnterprise(4),
	wpa2Enterprise(5), or radiusWep(6) when arrisRouterAdvancedRadiusCfg is enabled AND
	arrisRouterAdvancedRadiusCfg_SettingsEnable is true."

	INDEX { ifIndex }
	::= { arrisRouterAdvancedRadiusCfgSettingsTable 1 }

ArrisRouterAdvancedRadiusCfgSettingsEntry ::=
	SEQUENCE   {
		arrisRouterAdvancedRadiusCfgSettingsServerRetries               Unsigned32,
		arrisRouterAdvancedRadiusCfgSettingsServerRequestTimeout        Unsigned32,
		arrisRouterAdvancedRadiusCfgSettingsPMKLifetime                 Unsigned32,
		arrisRouterAdvancedRadiusCfgSettingsPMKCaching                  Unsigned32,
		arrisRouterAdvancedRadiusCfgSettingsPMKCacheInterval            Unsigned32,
		arrisRouterAdvancedRadiusCfgSettingsMaxAuthAttempts             Unsigned32,
		arrisRouterAdvancedRadiusCfgSettingsBlacklistTimeout            Unsigned32,
		arrisRouterAdvancedRadiusCfgSettingsIDRequestRetryInterval      Unsigned32,
		arrisRouterAdvancedRadiusCfgSettingsQuietPeriodAfterFailedAuth  Unsigned32
		}

arrisRouterAdvancedRadiusCfgSettingsServerRetries OBJECT-TYPE
    SYNTAX      Unsigned32 (0..20)
    MAX-ACCESS  read-write
    STATUS      current
    DESCRIPTION
        "Number of retries for Radius Requests."
    DEFVAL { 3 }
    ::= { arrisRouterAdvancedRadiusCfgSettingsEntry 2 }

arrisRouterAdvancedRadiusCfgSettingsServerRequestTimeout OBJECT-TYPE
    SYNTAX      Unsigned32 (0..60)
    MAX-ACCESS  read-write
    STATUS      current
    DESCRIPTION
        "Radius request timeout in seconds after which the request must be retransmitted
        for the number of retries available."
    DEFVAL { 5 }
    ::= { arrisRouterAdvancedRadiusCfgSettingsEntry 3 }

arrisRouterAdvancedRadiusCfgSettingsPMKLifetime OBJECT-TYPE
    SYNTAX      Unsigned32 (0..86400)
    MAX-ACCESS  read-write
    STATUS      current
    DESCRIPTION
        "Default time in seconds after which a Wi-Fi client is forced to re-authenticate
        (default 8 hours)"
    DEFVAL { 28800 }
    ::= { arrisRouterAdvancedRadiusCfgSettingsEntry 4 }

arrisRouterAdvancedRadiusCfgSettingsPMKCaching OBJECT-TYPE
    SYNTAX      Unsigned32 (0..1)
    MAX-ACCESS  read-write
    STATUS      current
    DESCRIPTION
    	"Enable or Disable Caching of PMK"
    DEFVAL { 0 }
    ::= { arrisRouterAdvancedRadiusCfgSettingsEntry 5 }

arrisRouterAdvancedRadiusCfgSettingsPMKCacheInterval OBJECT-TYPE
    SYNTAX      Unsigned32 (0..86400)
    MAX-ACCESS  read-write
    STATUS      current
    DESCRIPTION
        "Time interval in seconds after which the PMKSA (Pairwise Master Key Security
        Association) cache is purged (default 5 minutes)"
    DEFVAL { 300 }
    ::= { arrisRouterAdvancedRadiusCfgSettingsEntry 6 }

arrisRouterAdvancedRadiusCfgSettingsMaxAuthAttempts OBJECT-TYPE
    SYNTAX      Unsigned32 (0..32)
    MAX-ACCESS  read-write
    STATUS      current
    DESCRIPTION
        "Indicates the # of times, a client can attempt to login with incorrect
        credentials. When this limit is reached, the client is blacklisted and not
        allowed to attempt loging into the network. Setting this parameter to 0 (zero)
        disables the blacklisting feature."
    DEFVAL { 3 }
    ::= { arrisRouterAdvancedRadiusCfgSettingsEntry 7 }

arrisRouterAdvancedRadiusCfgSettingsBlacklistTimeout OBJECT-TYPE
    SYNTAX      Unsigned32 (0..1440)
    MAX-ACCESS  read-write
    STATUS      current
    DESCRIPTION
        "Time interval in minutes for which a client will continue to be blacklisted
        once it is marked so. Default Value is 10 minutes"
    DEFVAL { 10 }
    ::= { arrisRouterAdvancedRadiusCfgSettingsEntry 8 }

arrisRouterAdvancedRadiusCfgSettingsIDRequestRetryInterval OBJECT-TYPE
    SYNTAX      Unsigned32 (0..60)
    MAX-ACCESS  read-write
    STATUS      current
    DESCRIPTION
        "Time Interval in seconds between identity requests retries. A value of 0 (zero)
        disables it."
    DEFVAL { 5 }
    ::= { arrisRouterAdvancedRadiusCfgSettingsEntry 9 }

arrisRouterAdvancedRadiusCfgSettingsQuietPeriodAfterFailedAuth OBJECT-TYPE
    SYNTAX      Unsigned32 (0..60)
    MAX-ACCESS  read-write
    STATUS      current
    DESCRIPTION
        "The enforced quiet period (time interval) in seconds following failed
        authentication. A value of 0 (zero) disables it."
    DEFVAL { 5 }
    ::= { arrisRouterAdvancedRadiusCfgSettingsEntry 10 }

arrisRouterAdvancedRadiusCfgAccountingServerTable OBJECT-TYPE
    SYNTAX      SEQUENCE OF ArrisRouterAdvancedRadiusCfgAccountingServerEntry
    MAX-ACCESS  not-accessible
    STATUS      current
    DESCRIPTION
        "A table used to configure Radius Accounting Servers on a Per BSS Basis."
    ::= { arrisRouterAdvancedRadiusCfg 12 }

arrisRouterAdvancedRadiusCfgAccountingServerEntry OBJECT-TYPE
    SYNTAX      ArrisRouterAdvancedRadiusCfgAccountingServerEntry
    MAX-ACCESS  not-accessible
    STATUS      current
    DESCRIPTION
        "This table assigns Radius Accounting Server(s) to a BSS.  Utilized when
        arrisRouterAdvancedRadiusCfg is enabled AND Bit 3 is set TRUE."
    INDEX { ifIndex }
    ::= { arrisRouterAdvancedRadiusCfgAccountingServerTable 1 }

ArrisRouterAdvancedRadiusCfgAccountingServerEntry ::=
    SEQUENCE    {
        arrisRouterAdvancedRadiusCfgAccntSvrTableIndex                  Integer32,
        arrisRouterAdvancedRadiusCfgAccntSvrAddressType                 InetAddressType,
        arrisRouterAdvancedRadiusCfgAccntSvrAddress                     InetAddress,
        arrisRouterAdvancedRadiusCfgAccntSvrPort                        Unsigned32,
        arrisRouterAdvancedRadiusCfgAccntSvrKey                         DisplayString,
        arrisRouterAdvancedRadiusCfgAccntSvrReportInterval              Unsigned32
        }

arrisRouterAdvancedRadiusCfgAccntSvrTableIndex OBJECT-TYPE
    SYNTAX      Integer32 (1..4)
    MAX-ACCESS  not-accessible
    STATUS      current
    DESCRIPTION
        "Index used to order the Advanced Radius Server entries. Max 4 allowed per BSS."
    ::= { arrisRouterAdvancedRadiusCfgAccountingServerEntry 1 }

arrisRouterAdvancedRadiusCfgAccntSvrAddressType OBJECT-TYPE
    SYNTAX      InetAddressType
    MAX-ACCESS  read-write
    STATUS      current
    DESCRIPTION
        "The type of internet address type used for Accounting Server Address for this entry."
    ::= { arrisRouterAdvancedRadiusCfgAccountingServerEntry 2 }

arrisRouterAdvancedRadiusCfgAccntSvrAddress OBJECT-TYPE
    SYNTAX      InetAddress
    MAX-ACCESS  read-write
    STATUS      current
    DESCRIPTION
        "The internet address of the Accounting server for this entry."
    ::= { arrisRouterAdvancedRadiusCfgAccountingServerEntry 3 }

arrisRouterAdvancedRadiusCfgAccntSvrPort OBJECT-TYPE
    SYNTAX      Unsigned32
    MAX-ACCESS  read-write
    STATUS      current
    DESCRIPTION
        "The UDP port used to communicate with the Accounting server for this entry."
    DEFVAL { 1813 }
    ::= { arrisRouterAdvancedRadiusCfgAccountingServerEntry 4 }

arrisRouterAdvancedRadiusCfgAccntSvrKey OBJECT-TYPE
    SYNTAX      DisplayString (SIZE(1..64))
    MAX-ACCESS  read-write
    STATUS      current
    DESCRIPTION
        "The Accounting Server Authentiction key for this entry.  Read returns null string."
    ::= { arrisRouterAdvancedRadiusCfgAccountingServerEntry 5 }

arrisRouterAdvancedRadiusCfgAccntSvrReportInterval  OBJECT-TYPE
    SYNTAX      Unsigned32 (0..28800)
    MAX-ACCESS  read-write
    STATUS      current
    DESCRIPTION
        "Time Interval in seconds between Report generation.  Note per RFC-2869 The value
        MUST NOT be smaller than 60.  The value SHOULD NOT be smaller than 600, and careful
        consideration should be given to its impact on network traffic.  A value of 0 (zero)
        configured in this field shall indicate that the report interval should be taken from
        the Acct-Interim-Interval RADIUS attribute embedded within the Access-Accept Radius
        Server response to an Access-Request Message."
    DEFVAL { 600 }
    ::= { arrisRouterAdvancedRadiusCfgAccountingServerEntry 6 }

arrisRouterAdvancedRadiusCfgAuthStatsTable OBJECT-TYPE
    SYNTAX          SEQUENCE OF ArrisRouterAdvancedRadiusCfgAuthStatsEntry
    MAX-ACCESS      not-accessible
    STATUS          current
    DESCRIPTION
        "A table used to report Radius Authenticator Statistics related to the BSS.  Active when
        arrisRouterAdvancedRadiusCfg is enabled AND Bit 5 is TRUE."
    ::= { arrisRouterAdvancedRadiusCfg 14 }

arrisRouterAdvancedRadiusCfgAuthStatsEntry OBJECT-TYPE
    SYNTAX          ArrisRouterAdvancedRadiusCfgAuthStatsEntry
    MAX-ACCESS  not-accessible
    STATUS          current
    DESCRIPTION
        "This table reports statistics related to the radius server on a per BSS Basis.
        Should only be enabled if the AdvanceRadiusCfg is set true for this BSS AND Bit 5 is TRUE."
    INDEX { ifIndex }
    ::= { arrisRouterAdvancedRadiusCfgAuthStatsTable 1 }

ArrisRouterAdvancedRadiusCfgAuthStatsEntry ::=
        SEQUENCE        {
          arrisRouterAdvancedRadiusCfgAuthStatsValid                            TruthValue,
          arrisRouterAdvancedRadiusCfgAuthStatsFailedAuths                      Unsigned32,
          arrisRouterAdvancedRadiusCfgAuthStatsTimeouts                         Unsigned32,
          arrisRouterAdvancedRadiusCfgAuthStatsLatencyMaximum                   Unsigned32,
          arrisRouterAdvancedRadiusCfgAuthStatsLatencyAverage                   Unsigned32
          }

arrisRouterAdvancedRadiusCfgAuthStatsValid OBJECT-TYPE
    SYNTAX          TruthValue
    MAX-ACCESS      read-write
    STATUS          current
    DESCRIPTION
        "Marks this entry as valid.  All BSS's without Enterprise Encryption should be
        set as false.  Should be marked as Valid as soon as statistics are posted."
    DEFVAL { false }
    ::= { arrisRouterAdvancedRadiusCfgAuthStatsEntry 1 }

arrisRouterAdvancedRadiusCfgAuthStatsFailedAuths  OBJECT-TYPE
    SYNTAX      Unsigned32
    MAX-ACCESS  read-write
    STATUS      current
    DESCRIPTION
        "Number of failed Authentications via Radius associated with this BSS."
    ::= { arrisRouterAdvancedRadiusCfgAuthStatsEntry 2 }

arrisRouterAdvancedRadiusCfgAuthStatsTimeouts  OBJECT-TYPE
    SYNTAX      Unsigned32
    MAX-ACCESS  read-write
    STATUS      current
    DESCRIPTION
        "Number of Radius Timeouts for the Radius Server associated with this BSS."
    ::= { arrisRouterAdvancedRadiusCfgAuthStatsEntry 3 }

arrisRouterAdvancedRadiusCfgAuthStatsLatencyMaximum  OBJECT-TYPE
    SYNTAX      Unsigned32
    MAX-ACCESS  read-write
    STATUS      current
    DESCRIPTION
        "Maximum Latency Recorded for an Authentication via the Radius on this BSS."
    ::= { arrisRouterAdvancedRadiusCfgAuthStatsEntry 4 }

arrisRouterAdvancedRadiusCfgAuthStatsLatencyAverage  OBJECT-TYPE
    SYNTAX      Unsigned32
    MAX-ACCESS  read-write
    STATUS      current
    DESCRIPTION
        "Average Latency for all Authentications via the Radius on this BSS."
    ::= { arrisRouterAdvancedRadiusCfgAuthStatsEntry 5 }

-- End of arrisRouterAdvancedRadiusCfg

-- Enterprise Class Feature Control 2.4 GHz Radio
arrisRouterWifiEnterpriseRadioCfg OBJECT IDENTIFIER ::= { arrisRouterWirelessCfg 74 }

arrisRouterWifiRadioEnterpriseANI OBJECT-TYPE
       SYNTAX      TruthValue
       MAX-ACCESS  read-write
       STATUS      current
       DESCRIPTION
              " Enable Adaptive Noise Immunity 2.4 GHz Radio"
       DEFVAL { false }
       ::= { arrisRouterWifiEnterpriseRadioCfg 1 }

-- Note space left here for definition of the ANI Parameters and other items

arrisRouterWifi50EnterpriseRadioCfg OBJECT IDENTIFIER ::= { arrisRouterWirelessCfg 75 }

arrisRouterWifi50RadioEnterpriseANI OBJECT-TYPE
       SYNTAX      TruthValue
       MAX-ACCESS  read-write
       STATUS      current
       DESCRIPTION
              " Enable Adaptive Noise Immunity 5.0 GHz Radio"
       DEFVAL { false }
       ::= { arrisRouterWifi50EnterpriseRadioCfg 1 }

-- Note space left here for definition of the ANI Parameters and other items
arrisRouterWiFiTransmitPowerInDecibel OBJECT-TYPE
     SYNTAX      INTEGER (0..30)
     UNITS       "Decibels"
     MAX-ACCESS  read-write
     STATUS      current
     DESCRIPTION "Configures Wi-Fi transmit power in steps of 1dB for 2.4 radio."
     DEFVAL { 30 }
     ::= { arrisRouterWirelessCfg 76 }

arrisRouterPassPointEntry OBJECT IDENTIFIER ::= { arrisRouterWirelessCfg 77 }

arrisRouterPassPointEnable OBJECT-TYPE
     SYNTAX      TruthValue
     MAX-ACCESS  read-write
     STATUS      current
     DESCRIPTION "Enable or disable the Passpoint2.0 feature."
     DEFVAL { false }
     ::= { arrisRouterPassPointEntry 1 }

arrisRouterInterworkingEnable OBJECT-TYPE
     SYNTAX      TruthValue
     MAX-ACCESS  read-write
     STATUS      current
     DESCRIPTION "Enable or disable the Interworking feature."
     DEFVAL { false }
     ::= { arrisRouterPassPointEntry 2 }

arrisRouterRadiusSecondaryTable   OBJECT-TYPE
    SYNTAX      SEQUENCE OF ArrisRouterRadiusSecondaryEntry
    MAX-ACCESS  not-accessible
    STATUS      current
    DESCRIPTION
        "A table used to configure settings related to the Secondary RADIUS security
         modes, including WPA-Enterprise, WPA2-Enterprise and RADIUS-WEP."
    ::= { arrisRouterWirelessCfg 78 }

arrisRouterRadiusSecondaryEntry OBJECT-TYPE
    SYNTAX      ArrisRouterRadiusSecondaryEntry
    MAX-ACCESS  not-accessible
    STATUS      current
    DESCRIPTION
        "An entry defining the Secondary RADIUS characteristics of an individual service
         set.  A row exists in this table for each row in the arrisRouterBSSTable
         for which arrisRouterWiFiSecurityMode is set to wpaEnterprise(4),
         wpa2Enterprise(5), or radiusWep(6)."
    INDEX   { ifIndex }
    ::= { arrisRouterRadiusSecondaryTable 1 }

ArrisRouterRadiusSecondaryEntry ::=
    SEQUENCE    {
                arrisRouterRadiusSecondaryAddressType       InetAddressType,
                arrisRouterRadiusSecondaryAddress           InetAddress,
                arrisRouterRadiusSecondaryPort              Unsigned32,
                arrisRouterRadiusSecondaryKey               DisplayString
    }

arrisRouterRadiusSecondaryAddressType OBJECT-TYPE
    SYNTAX      InetAddressType
    MAX-ACCESS  read-write
    STATUS      current
    DESCRIPTION
        "The type of internet address used for arrisRouterRadiusSecondaryAddress."
    ::= { arrisRouterRadiusSecondaryEntry 1 }

arrisRouterRadiusSecondaryAddress OBJECT-TYPE
    SYNTAX      InetAddress
    MAX-ACCESS  read-write
    STATUS      current
    DESCRIPTION
        "The internet address of the Secondary RADIUS server for this service set."
    ::= { arrisRouterRadiusSecondaryEntry 2 }

arrisRouterRadiusSecondaryPort OBJECT-TYPE
    SYNTAX      Unsigned32
    MAX-ACCESS  read-write
    STATUS      current
    DESCRIPTION
        "The UDP port used to communicate with the Secondary RADIUS server for this
         service set."
    ::= { arrisRouterRadiusSecondaryEntry 3 }

arrisRouterRadiusSecondaryKey OBJECT-TYPE
    SYNTAX      DisplayString (SIZE(1..64))
    MAX-ACCESS  read-write
    STATUS      current
    DESCRIPTION
        "The Secondary RADIUS key."
    ::= { arrisRouterRadiusSecondaryEntry 4 }

arrisRouterWiFiAutoChannelList OBJECT-TYPE
    SYNTAX       DisplayString(SIZE(0..255))
    MAX-ACCESS   read-write
    STATUS       current
    DESCRIPTION "Restricted available channel list for 2.4G radio (not all avail) from which to select a channel
                 when arrisRouterWiFiChannel is set to Auto-channel(0) mode. Space separated list.For 802.11b/g/n,
                 avail channels are 1-14. E.g. 1 6 11. An empty string denotes utilizing default country channels.
                 Included channels which are not in the default country channels shall be ignored."
    ::= { arrisRouterWirelessCfg 79 }

arrisRouterSTASteerCmd OBJECT IDENTIFIER ::= { arrisRouterWirelessCfg 80 }

arrisRouterSteerAP OBJECT-TYPE
    SYNTAX      Integer32
    MAX-ACCESS  read-write
    STATUS      current
    DESCRIPTION
        "The ifIndex of the AP to steer the STA from"
    ::= { arrisRouterSTASteerCmd 1 }

arrisRouterSteerSTA OBJECT-TYPE
    SYNTAX      MacAddress
    MAX-ACCESS  read-create
    STATUS      current
    DESCRIPTION
        "The MAC address of the station to be steered."
    ::= { arrisRouterSTASteerCmd 2 }

arrisRouterSteerType OBJECT-TYPE
    SYNTAX      INTEGER
    MAX-ACCESS  read-write
    STATUS      current
    DESCRIPTION
       "The type of steering to invoke.
           0 = Blacklist
           1 = BssTransitionRequest
           2 = MBO Operational Steer"
    ::= { arrisRouterSTASteerCmd 3 }

arrisRouterSteerExecute OBJECT-TYPE
    SYNTAX      TruthValue
    MAX-ACCESS  read-write
    STATUS      current
    DESCRIPTION
        "Execute the Steer. Software should reset this to false once steer is executed.
         When Value is true, no new steering commands may be accepted."
    DEFVAL { false }
    ::= { arrisRouterSTASteerCmd 4 }

arrisRouterSTASteerBlacklistCmd OBJECT IDENTIFIER ::= { arrisRouterSTASteerCmd 10 }

arrisRouterSteerBlacklistAction OBJECT-TYPE
    SYNTAX      INTEGER
    MAX-ACCESS  read-write
    STATUS      current
    DESCRIPTION
       "What to do with the Blacklist STA.
           0 = Remove from Blacklist
           1 = Add to Blacklist
           2 = Add to Blacklist for a Period of Time"
    ::= { arrisRouterSTASteerBlacklistCmd 1 }

arrisRouterSteerBlacklistTimer OBJECT-TYPE
    SYNTAX      INTEGER
    MAX-ACCESS  read-write
    STATUS      current
    DESCRIPTION
       "How long to hold the STA in the blacklist (seconds).
           0 = No Timeout "
    ::= { arrisRouterSTASteerBlacklistCmd 2 }

arrisRouterRadiusAttributeTable   OBJECT-TYPE
    SYNTAX      SEQUENCE OF ArrisRouterRadiusAttributeEntry
    MAX-ACCESS  not-accessible
    STATUS      current
    DESCRIPTION
        "A table used to configure radius attributes"
    ::= { arrisRouterWirelessCfg 81 }

arrisRouterRadiusAttributeEntry OBJECT-TYPE
    SYNTAX      ArrisRouterRadiusAttributeEntry
    MAX-ACCESS  not-accessible
    STATUS      current
    DESCRIPTION
         "An entry defining the RADIUS attribute characteristics."
    INDEX   { ifIndex }
    ::= { arrisRouterRadiusAttributeTable 1 }

ArrisRouterRadiusAttributeEntry ::=
    SEQUENCE    {
                arrisRouterRadiusAttributeOperatorName            DisplayString,
                arrisRouterRadiusAttributeLocationInformation     DisplayString,
                arrisRouterRadiusAttributeLocationData            DisplayString
    }

arrisRouterRadiusAttributeOperatorName OBJECT-TYPE
    SYNTAX      DisplayString (SIZE(1..64))
    MAX-ACCESS  read-write
    STATUS      current
    DESCRIPTION
        "The radius Attribute operator name"
    ::= { arrisRouterRadiusAttributeEntry 1 }

arrisRouterRadiusAttributeLocationInformation OBJECT-TYPE
    SYNTAX      DisplayString (SIZE(1..64))
    MAX-ACCESS  read-write
    STATUS      current
    DESCRIPTION
        "The radius Attribute location information"
    ::= { arrisRouterRadiusAttributeEntry 2 }

arrisRouterRadiusAttributeLocationData OBJECT-TYPE
    SYNTAX      DisplayString (SIZE(1..64))
    MAX-ACCESS  read-write
    STATUS      current
    DESCRIPTION
        "The radius Attribute location data"
    ::= { arrisRouterRadiusAttributeEntry 3 }

arrisRouterInterworkingIECfg OBJECT IDENTIFIER ::= { arrisRouterWirelessCfg 82 }

arrisRouterInterworkingCapable OBJECT-TYPE
    SYNTAX      TruthValue
    MAX-ACCESS  read-only
    STATUS      current
    DESCRIPTION "Indicates support of this device for Interworking feature."
    DEFVAL { false }
    ::= { arrisRouterInterworkingIECfg 1 }

arrisRouterInterworkingIEBSSTable OBJECT-TYPE
    SYNTAX          SEQUENCE OF ArrisRouterInterworkingIEBSSEntry
    MAX-ACCESS      not-accessible
    STATUS          current
    DESCRIPTION
        "This table assigns Interworking IE parameters to the BSS."
    ::= { arrisRouterInterworkingIECfg 5 }

arrisRouterInterworkingIEBSSEntry OBJECT-TYPE
    SYNTAX          ArrisRouterInterworkingIEBSSEntry
    MAX-ACCESS      not-accessible
    STATUS          current
    DESCRIPTION
        "A row in the table of the arrisRouterInterworkingIEBSSTable."
    INDEX { ifIndex }       --from IF-MIB
    ::= { arrisRouterInterworkingIEBSSTable 1 }

ArrisRouterInterworkingIEBSSEntry ::=
    SEQUENCE        {
      arrisRouterInterworkingIEEnable                       TruthValue,
      arrisRouterInterworkingIEAccessNetworkType            INTEGER,
      arrisRouterInterworkingIEInternetAccess               TruthValue,
      arrisRouterInterworkingIEASRA                         TruthValue,
      arrisRouterInterworkingIEESR                          TruthValue,
      arrisRouterInterworkingIEUESA                         TruthValue,
      arrisRouterInterworkingIEVenueGroupCode               INTEGER,
      arrisRouterInterworkingIEVenueTypeCode                INTEGER,
      arrisRouterInterworkingIEHESSID                       DisplayString
    }

arrisRouterInterworkingIEEnable OBJECT-TYPE
    SYNTAX          TruthValue
    MAX-ACCESS      read-write
    STATUS          current
    DESCRIPTION
        "Enable Broadcast of Interworking IE for this BSS"
    DEFVAL { false }
    ::= { arrisRouterInterworkingIEBSSEntry 1 }


arrisRouterInterworkingIEAccessNetworkType OBJECT-TYPE
    SYNTAX          INTEGER (0..15)
    MAX-ACCESS      read-write
    STATUS          current
    DESCRIPTION
        "The Access Network Type as defined in 802.11-2012 Table 8-174"
    DEFVAL { 0 }
    ::= { arrisRouterInterworkingIEBSSEntry 2 }

arrisRouterInterworkingIEInternetAccess OBJECT-TYPE
    SYNTAX          TruthValue
    MAX-ACCESS      read-write
    STATUS          current
    DESCRIPTION
        "Advertise connectivity to the Internet on this BSS per 802.11-2012 8.4.2.94"
    DEFVAL { false }
    ::= { arrisRouterInterworkingIEBSSEntry 3 }

arrisRouterInterworkingIEASRA OBJECT-TYPE
    SYNTAX          TruthValue
    MAX-ACCESS      read-write
    STATUS          current
    DESCRIPTION
        "Advertise Additional Step Required for Access on this BSS per 802.11-2012 8.4.2.94"
    DEFVAL { false }
    ::= { arrisRouterInterworkingIEBSSEntry 4 }

arrisRouterInterworkingIEESR OBJECT-TYPE
    SYNTAX          TruthValue
    MAX-ACCESS      read-write
    STATUS          current
    DESCRIPTION
        "Advertise Emergency Services Reachable on this BSS per 802.11-2012 8.4.2.94"
    DEFVAL { false }
    ::= { arrisRouterInterworkingIEBSSEntry 5 }

arrisRouterInterworkingIEUESA OBJECT-TYPE
    SYNTAX          TruthValue
    MAX-ACCESS      read-write
    STATUS          current
    DESCRIPTION
        "Advertise Unauthenticated Emergency Service Accessible on this BSS per 802.11-2012 8.4.2.94"
    DEFVAL { false }
    ::= { arrisRouterInterworkingIEBSSEntry 6 }

arrisRouterInterworkingIEVenueGroupCode OBJECT-TYPE
    SYNTAX          INTEGER (0..11)
    MAX-ACCESS      read-write
    STATUS          current
    DESCRIPTION
        "The Venue Group Code as defined in 802.11-2012 8.4.1.34"
    DEFVAL { 0 }
    ::= { arrisRouterInterworkingIEBSSEntry 7 }

arrisRouterInterworkingIEVenueTypeCode OBJECT-TYPE
    SYNTAX          INTEGER (0..255)
    MAX-ACCESS      read-write
    STATUS          current
    DESCRIPTION
        "The Venu Type Code as defined in 802.11-2012 8.4.1.34"
    DEFVAL { 0 }
    ::= { arrisRouterInterworkingIEBSSEntry 8 }

arrisRouterInterworkingIEHESSID OBJECT-TYPE
    SYNTAX          DisplayString (SIZE (0..17))
    MAX-ACCESS      read-write
    STATUS          current
    DESCRIPTION
        "The HESSID as defined in 802.11-2012 8.4.2.94"
    ::= { arrisRouterInterworkingIEBSSEntry 9 }

arrisRouterWiFiMgmtFramePower OBJECT-TYPE
        SYNTAX      Unsigned32(0..255)
        MAX-ACCESS  read-write
        STATUS      current
        DESCRIPTION
                "Configure the Management Frame Power value for all Frames. Power range from 0 to 255"
        DEFVAL { 255 }
   ::= { arrisRouterWirelessCfg 83 }

arrisRouterAirtimeCtrlCfg OBJECT IDENTIFIER ::= { arrisRouterWirelessCfg 99 }

arrisRouterAirtimeCtrlBSSIDEnable OBJECT-TYPE
     SYNTAX      TruthValue
     MAX-ACCESS  read-write
     STATUS      current
     DESCRIPTION "Enable or disable the BSSID airtime management feature."
     DEFVAL { false }
     ::= { arrisRouterAirtimeCtrlCfg 1 }

arrisRouterAirtimeCtrlBSSIDWeightTable OBJECT-TYPE
	SYNTAX		SEQUENCE OF ArrisRouterAirtimeCtrlBSSIDWeightEntry
	MAX-ACCESS 	not-accessible
	STATUS		current
	DESCRIPTION
		"This table assigns bandwidth allocation percentage to the BSSID."
	::= { arrisRouterAirtimeCtrlCfg 2 }

arrisRouter50AirtimeCtrlBSSIDEnable OBJECT-TYPE
     SYNTAX      TruthValue
     MAX-ACCESS  read-write
     STATUS      current
     DESCRIPTION "Enable or disable the 5G BSSID airtime management feature."
     DEFVAL { false }
     ::= { arrisRouterAirtimeCtrlCfg 3 }

arrisRouterAirtimeCtrlBSSIDWeightEntry OBJECT-TYPE
	SYNTAX		ArrisRouterAirtimeCtrlBSSIDWeightEntry
	MAX-ACCESS  not-accessible
	STATUS		current
	DESCRIPTION
		"A row in the table of the arrisRouterAirtimeCtrlBSSIDMappingTable."
    INDEX { ifIndex }	--from IF-MIB
	::= { arrisRouterAirtimeCtrlBSSIDWeightTable 1 }

ArrisRouterAirtimeCtrlBSSIDWeightEntry ::=
	SEQUENCE	{
				  arrisRouterAirtimeCtrlBSSIDWeightGuaranteedPercentage		Unsigned32,
				  arrisRouterAirtimeCtrlBSSIDWeightMaximumPercentage	    Unsigned32
	            }

arrisRouterAirtimeCtrlBSSIDWeightGuaranteedPercentage OBJECT-TYPE
	SYNTAX		Unsigned32 (0..100)
	MAX-ACCESS	read-write
	STATUS		current
	DESCRIPTION
		"The minimum percentage of airtime allocated to the BSSID during periods of congestion."
	DEFVAL { 0 }
   ::= { arrisRouterAirtimeCtrlBSSIDWeightEntry 1 }

arrisRouterAirtimeCtrlBSSIDWeightMaximumPercentage OBJECT-TYPE
     SYNTAX      Unsigned32 (0..100)
     MAX-ACCESS  read-write
     STATUS      current
     DESCRIPTION "The maximum percentage of airtime allocated to the BSSID during periods of non-congestion."
	 DEFVAL { 100 }
     ::= { arrisRouterAirtimeCtrlBSSIDWeightEntry 2 }

arrisRouterWifiLogs OBJECT IDENTIFIER ::= { arrisRouterWirelessCfg 100 }

arrisRouterWifiEventlogcontrol OBJECT-TYPE
     SYNTAX         INTEGER { resetLog(1) }
     MAX-ACCESS     read-write
     STATUS         current
     DESCRIPTION    "Setting this object to resetLog(1) empties the event log. Reading this object always returns resetLog(1)."
     DEFVAL { 1 }
     ::= { arrisRouterWifiLogs 1 }

arrisRouterWifiEventSeverityControl OBJECT-TYPE
     SYNTAX         Integer32 (1..7)
     MAX-ACCESS     read-write
     STATUS         current
     DESCRIPTION    "Setting the minimum level that is recorded in the event log.
                     Default value: 4
                     If a subsystem encounters an event that would generate an log entry at level 7, this event will not be recorded in the WiFi event log. Reading this object returns the current level."
     DEFVAL { 4 }
     ::= { arrisRouterWifiLogs 2 }

arrisRouterWifiLogTable OBJECT-TYPE
     SYNTAX		SEQUENCE OF ArrisRouterWifiLogEntry
     MAX-ACCESS 	not-accessible
     STATUS		current
     DESCRIPTION
     "This table display human-readable description of the event"
     ::= { arrisRouterWifiLogs 3 }

arrisRouterWifiLogEntry OBJECT-TYPE
     SYNTAX		ArrisRouterWifiLogEntry
     MAX-ACCESS not-accessible
     STATUS		current
     DESCRIPTION
     "A row in the table of the WiFi event log table."

     INDEX { arrisRouterWifiEventLogIndex }
	   ::= { arrisRouterWifiLogTable 1 }

ArrisRouterWifiLogEntry ::=
     SEQUENCE	{
		  	        arrisRouterWifiEventLogIndex           Unsigned32,
		  	        arrisRouterWifiEventLogInfo            DisplayString
     }

arrisRouterWifiEventLogIndex OBJECT-TYPE
     SYNTAX      Unsigned32 (1..50)
     MAX-ACCESS  not-accessible
     STATUS      current
     DESCRIPTION "Provides relative ordering of the objects in the event log.
                 This object will always increase except when (a) the log is reset via cmdot11EventLogsControl, b) it reaches the value 50"
     ::= { arrisRouterWifiLogEntry 1 }

arrisRouterWifiEventLogInfo OBJECT-TYPE
     SYNTAX     DisplayString (SIZE(0..255))
     MAX-ACCESS	read-only
     STATUS		current
     DESCRIPTION "Provides a human-readable description of the event."
     ::= { arrisRouterWifiLogEntry 2 }

-- ADD START, PD13996
arrisRouterAdvAirtimeClientStatistics OBJECT IDENTIFIER ::= { arrisRouterAirtimeCtrlCfg 103 }

arrisRouterAdvAirtimeClientStatisticsTable OBJECT-TYPE
     SYNTAX		SEQUENCE OF ArrisRouterAdvAirtimeClientStatisticsEntry
     MAX-ACCESS not-accessible
     STATUS		current
     DESCRIPTION
    		"This table allows readback of Airtime Statistics for individual clients"
     ::= { arrisRouterAdvAirtimeClientStatistics 1 }

arrisRouterAdvAirtimeClientStatisticsEntry OBJECT-TYPE
	 SYNTAX		ArrisRouterAdvAirtimeClientStatisticsEntry
	 MAX-ACCESS  not-accessible
	 STATUS		current
	 DESCRIPTION
		"A Row in the table reporting Airtime Management Client Statistics."

     INDEX { arrisRouterAdvAirtimeStatsClIndex	  }
	::= { arrisRouterAdvAirtimeClientStatisticsTable 1 }

ArrisRouterAdvAirtimeClientStatisticsEntry ::=
     SEQUENCE	{
		  	        arrisRouterAdvAirtimeStatsClIndex               Unsigned32,
		  	        arrisRouterAdvAirtimeStatsClMAC	                MacAddress,
		  	        arrisRouterAdvAirtimeStatsClWeight              Unsigned32,
		  	        arrisRouterAdvAirtimeStatsClSSID                DisplayString,
		  	        arrisRouterAdvAirtimeStatsClBSSWeight           Unsigned32,
		  	        arrisRouterAdvAirtimeStatsClAirtimeShortAvg     Unsigned32,
		  	        arrisRouterAdvAirtimeStatsClAirtimeTotal        Unsigned32
		  	    }

arrisRouterAdvAirtimeStatsClIndex OBJECT-TYPE
    SYNTAX      Unsigned32 (1..50)
    MAX-ACCESS  not-accessible
    STATUS      current
    DESCRIPTION "The Index assigned to the Client Entry"
    ::= { arrisRouterAdvAirtimeClientStatisticsEntry 1 }

arrisRouterAdvAirtimeStatsClMAC OBJECT-TYPE
     SYNTAX		MacAddress
     MAX-ACCESS	read-only
     STATUS		current
     DESCRIPTION "MAC Address of the Client"
    ::= { arrisRouterAdvAirtimeClientStatisticsEntry 2 }

arrisRouterAdvAirtimeStatsClWeight OBJECT-TYPE
     SYNTAX		Unsigned32
     MAX-ACCESS	read-only
     STATUS		current
     DESCRIPTION "The Weight Assigned to this Client (if any)"
    ::= { arrisRouterAdvAirtimeClientStatisticsEntry 3 }

arrisRouterAdvAirtimeStatsClSSID OBJECT-TYPE
     SYNTAX		DisplayString
     MAX-ACCESS	read-only
     STATUS		current
     DESCRIPTION "The SSID the client is associated to"
    ::= { arrisRouterAdvAirtimeClientStatisticsEntry 4 }

arrisRouterAdvAirtimeStatsClBSSWeight OBJECT-TYPE
     SYNTAX		Unsigned32
     MAX-ACCESS	read-only
     STATUS		current
     DESCRIPTION "The Weight assigned to the BSS where this Client is associated"
    ::= { arrisRouterAdvAirtimeClientStatisticsEntry 5 }

arrisRouterAdvAirtimeStatsClAirtimeShortAvg OBJECT-TYPE
     SYNTAX		Unsigned32
     MAX-ACCESS	read-only
     STATUS		current
     DESCRIPTION "Measured Airtime of this client averaged across short measuring
                    window (less than 1 second)."
     DEFVAL { 0 }
    ::= { arrisRouterAdvAirtimeClientStatisticsEntry 6 }

arrisRouterAdvAirtimeStatsClAirtimeTotal OBJECT-TYPE
     SYNTAX		Unsigned32
     MAX-ACCESS	read-only
     STATUS		current
     DESCRIPTION "Total airtime from the time this client was first associated,
                    (in milliseconds)."
     DEFVAL { 0 }
    ::= { arrisRouterAdvAirtimeClientStatisticsEntry 7 }
-- ADD END, PD13996

arrisRouterEnterpriseCfg OBJECT IDENTIFIER ::= { arrisRouterWirelessCfg 105 }

arrisRouterBSSBeaconCfgTable OBJECT-TYPE
      SYNTAX          SEQUENCE OF ArrisRouterBSSBeaconCfgEntry
      MAX-ACCESS      not-accessible
      STATUS          current
      DESCRIPTION
          "A table used to configure per BSS Beacon Parameters.
          Enabled when arrisRouterBSSEnterpriseCfg is enabled and Bit 1 is set TRUE"
      ::= { arrisRouterEnterpriseCfg 10 }

arrisRouterBSSBeaconCfgEntry OBJECT-TYPE
      SYNTAX          ArrisRouterBSSBeaconCfgEntry
      MAX-ACCESS  not-accessible
      STATUS          current
      DESCRIPTION
          ""
      INDEX { ifIndex }
      ::= { arrisRouterBSSBeaconCfgTable 1 }

ArrisRouterBSSBeaconCfgEntry ::=  SEQUENCE    {
        arrisRouterBSSBeaconCfgSettings              Unsigned32,
        arrisRouterBSSBeaconCfgBeaconInterval        Unsigned32,
        arrisRouterBSSBeaconCfgDTIMInterval          Unsigned32
}

arrisRouterBSSBeaconCfgSettings OBJECT-TYPE
      SYNTAX          Unsigned32
      MAX-ACCESS      read-write
      STATUS          current
      DESCRIPTION
          "Beacon Configuration Items for this BSS
           0 = Default -- defaults BSS to match Radio Settings.
           1 = Set Beacon Interval.
           2 = Set Beacon Interval and DTIM Interval"
      DEFVAL { 0 }
      ::= { arrisRouterBSSBeaconCfgEntry 1 }

arrisRouterBSSBeaconCfgBeaconInterval  OBJECT-TYPE
    SYNTAX      Unsigned32 (50..65535)
    MAX-ACCESS  read-write
    STATUS      current
    DESCRIPTION
        "Beacon Interval in TUs (1024 uSec) for this BSS Beacon Transmission"
    DEFVAL { 100 }
    ::= { arrisRouterBSSBeaconCfgEntry 2 }

arrisRouterBSSBeaconCfgDTIMInterval OBJECT-TYPE
    SYNTAX      Unsigned32 (1..255)
    MAX-ACCESS  read-write
    STATUS      current
    DESCRIPTION "Amount of time between Delivery Traffic Indication Messages in Beacon intervals."
    DEFVAL { 1 }
    ::= { arrisRouterBSSBeaconCfgEntry 3 }

-- BSS Rate CFG
arrisRouterBSSRateCfgTable OBJECT-TYPE
      SYNTAX          SEQUENCE OF ArrisRouterBSSRateCfgEntry
      MAX-ACCESS      not-accessible
      STATUS          current
      DESCRIPTION
          "A table used to configure per BSS Supported Rates -- Legacy Supported, Legacy
          Basic, HT, VHT, etc.
          Enabled when arrisRouterBSSEnterpriseCfg is enabled and Bit 2 is set TRUE"
      ::= { arrisRouterEnterpriseCfg 20 }

arrisRouterBSSRateCfgEntry OBJECT-TYPE
      SYNTAX          ArrisRouterBSSRateCfgEntry
      MAX-ACCESS  not-accessible
      STATUS          current
      DESCRIPTION
          ""
      INDEX { ifIndex }
      ::= { arrisRouterBSSRateCfgTable 1 }

ArrisRouterBSSRateCfgEntry ::= SEQUENCE       {
        arrisRouterBSSRateCfgSettings              Unsigned32,
        arrisRouterBSSRateCfgLegacyRates           DisplayString,
        arrisRouterBSSRateCfgHTRates               DisplayString,
        arrisRouterBSSRateCfgVHTRates              DisplayString
        }

arrisRouterBSSRateCfgSettings OBJECT-TYPE
      SYNTAX      Unsigned32
      MAX-ACCESS      read-write
      STATUS          current
      DESCRIPTION
          "Rate Configuration Items for this BSS
           0 = Default -- defaults BSS to match Radio Settings.
           1 = Set Advertised Supported and Basic Rates -- for Legacy / Management rates.
           2 = Advanced Settings HT -- utilize advanced HT settings (unsupported at this time)
           3 = Advanced Settings HT & VHT -- Utilize both HT & VHT Advanced Settings (unsupported at this time)."
      DEFVAL { 0 }
      ::= { arrisRouterBSSRateCfgEntry 1 }

arrisRouterBSSRateCfgLegacyRates OBJECT-TYPE
      SYNTAX      DisplayString (SIZE(1..128))
      MAX-ACCESS      read-write
      STATUS          current
      DESCRIPTION
          " Define the Legacy (advertised) Supported and Basic Rates. Definition is a SPACE Separated List of rates (Mbps)
            The letter B denotes a Basic Rate.

            Examples -- 2.4 GHz Radio (B/G)
            '1B 2B 5.5SB 11B 6B 9 12B 18 24B 36 48 54'
            -- advertises 1,2,5.5,11,6,12,24 as basic rates -- 9,18,36,48,54 as supported

            '5.5B 11B 6B 9 12B 18 24B 36 48 54'
            -- advertises 5.5,11,6,12,24 as basic rates -- 9,18,36,48,54 as supported

            Example -- 2.4 GHZ, 5 GHZ Radio
            '6B 9 12B 18 24B 36 48 54'
            -- advertises 6,12,24 as basic rates -- 9,18,36,48,54 as supported
            -- For 2.4 GHz -- Disables B rates.
          "
      ::= { arrisRouterBSSRateCfgEntry 2 }

arrisRouterBSSRateCfgHTRates OBJECT-TYPE
      SYNTAX      DisplayString
      MAX-ACCESS      read-write
      STATUS          current
      DESCRIPTION " Unsupported at this time"
      ::= { arrisRouterBSSRateCfgEntry 3 }

arrisRouterBSSRateCfgVHTRates OBJECT-TYPE
      SYNTAX      DisplayString
      MAX-ACCESS      read-write
      STATUS          current
      DESCRIPTION " Unsupported at this time"
      ::= { arrisRouterBSSRateCfgEntry 4 }

-- BSS Power CFG
arrisRouterBSSPowerCfgTable OBJECT-TYPE
      SYNTAX          SEQUENCE OF ArrisRouterBSSPowerCfgEntry
      MAX-ACCESS      not-accessible
      STATUS          current
      DESCRIPTION
          "A table used to configure per BSS Supported Management Frame Powers.
          Enabled when arrisRouterBSSEnterpriseCfg is enabled and Bit 3 is set TRUE"
      ::= { arrisRouterEnterpriseCfg 30 }

arrisRouterBSSPowerCfgEntry OBJECT-TYPE
      SYNTAX          ArrisRouterBSSPowerCfgEntry
      MAX-ACCESS  not-accessible
      STATUS          current
      DESCRIPTION
          ""
      INDEX { ifIndex }
      ::= { arrisRouterBSSPowerCfgTable 1 }

ArrisRouterBSSPowerCfgEntry ::= SEQUENCE      {
        arrisRouterBSSPowerCfgSettings              Unsigned32,
        arrisRouterBSSPowerCfgPowerDecrement        Unsigned32
        }

arrisRouterBSSPowerCfgSettings OBJECT-TYPE
      SYNTAX      Unsigned32
      MAX-ACCESS      read-write
      STATUS          current
      DESCRIPTION
          "Power Configuration Items for this BSS
           0 = Default -- defaults BSS to match Radio Settings.
           1 = Decrement Management Frame Power per RouterBSSPowerCfg_PowerDecriment"
      DEFVAL { 0 }
      ::= { arrisRouterBSSPowerCfgEntry 1 }

arrisRouterBSSPowerCfgPowerDecrement OBJECT-TYPE
      SYNTAX      Unsigned32 (0..30)
      MAX-ACCESS      read-write
      STATUS          current
      DESCRIPTION
          "Amount of Power(dB) to subtract from Management Frames for this BSS."
      DEFVAL { 0 }
      ::= { arrisRouterBSSPowerCfgEntry 2 }

----------------------------------------------------------------------------------------
-- Passpoint Features
-- This object is used to configure the passpoint (802.11u) parameters for the Access Point.
----------------------------------------------------------------------------------------
arrisRouterBssPasspoint OBJECT IDENTIFIER ::= { arrisRouterWirelessCfg 106 }

arrisRouterPasspointCapable OBJECT-TYPE
      SYNTAX      TruthValue
      MAX-ACCESS      read-only
      STATUS          current
      DESCRIPTION
          "Indicates support of this device for Passpoint (Hotspot 2.0)."
      DEFVAL { true }
      ::= { arrisRouterBssPasspoint 1 }

arrisRouterBSSPasspointTable OBJECT-TYPE
      SYNTAX          SEQUENCE OF ArrisRouterBSSPasspointEntry
      MAX-ACCESS      not-accessible
      STATUS          current
      DESCRIPTION
          "A table of entries in support of Passpoint (Hotspot 2.0) status and configuration."
      ::= { arrisRouterBssPasspoint 10 }

arrisRouterBSSPasspointEntry OBJECT-TYPE
      SYNTAX          ArrisRouterBSSPasspointEntry
      MAX-ACCESS  not-accessible
      STATUS          current
      DESCRIPTION
          ""
      INDEX { ifIndex }
      ::= { arrisRouterBSSPasspointTable 1 }

ArrisRouterBSSPasspointEntry ::=
        SEQUENCE        {
        arrisRouterBssPasspointEnable              TruthValue,
        arrisRouterBssPasspointDGAFEnable          TruthValue,
        arrisRouterBssPasspointANQPDomainID        INTEGER,
        arrisRouterBssPasspointVenueNames          INTEGER,
        arrisRouterBssPasspointOperatorNames       INTEGER,
        arrisRouterBssPasspointConsortiumOIs       INTEGER,
        arrisRouterBssPasspointDomainNames         INTEGER,
        arrisRouterBssPasspoint3GPPNetworks        INTEGER,
        arrisRouterBssPasspointNAIRealmsCount      INTEGER,
        arrisRouterBssPasspointIPAddressAvailability  INTEGER
        }

arrisRouterBssPasspointEnable OBJECT-TYPE
      SYNTAX      TruthValue
      MAX-ACCESS      read-write
      STATUS          current
      DESCRIPTION
          "Activate Passpoint (Hotspot 2.0) for this interface."
      DEFVAL { false }
      ::= { arrisRouterBSSPasspointEntry 1 }

arrisRouterBssPasspointDGAFEnable OBJECT-TYPE
      SYNTAX      TruthValue
      MAX-ACCESS      read-write
      STATUS          current
      DESCRIPTION
          "Enable/Disable Downstream Group-Addressed Forwarding frames."
      DEFVAL { true }
      ::= { arrisRouterBSSPasspointEntry 2 }

arrisRouterBssPasspointANQPDomainID OBJECT-TYPE
      SYNTAX      INTEGER(-1..65535)
      MAX-ACCESS      read-write
      STATUS          current
      DESCRIPTION
          "Enable/Disable Downstream Group-Addressed Forwarding frames."
      DEFVAL { -1 }
      ::= { arrisRouterBSSPasspointEntry 3 }

arrisRouterBssPasspointVenueNames OBJECT-TYPE
      SYNTAX      INTEGER(0..10)
      MAX-ACCESS      read-write
      STATUS          current
      DESCRIPTION
          "The number of entries in the VenueNames table."
      DEFVAL { 0 }
      ::= { arrisRouterBSSPasspointEntry 4 }

arrisRouterBssPasspointOperatorNames OBJECT-TYPE
      SYNTAX      INTEGER(0..10)
      MAX-ACCESS      read-write
      STATUS          current
      DESCRIPTION
          "The number of entries in the OperatorNames table."
      DEFVAL { 0 }
      ::= { arrisRouterBSSPasspointEntry 5 }

arrisRouterBssPasspointConsortiumOIs  OBJECT-TYPE
      SYNTAX      INTEGER(0..10)
      MAX-ACCESS      read-write
      STATUS          current
      DESCRIPTION
          "The number of entries in the ConsortiumOIs table."
      DEFVAL { 0 }
      ::= { arrisRouterBSSPasspointEntry 6 }

arrisRouterBssPasspointDomainNames  OBJECT-TYPE
      SYNTAX      INTEGER(0..10)
      MAX-ACCESS      read-write
      STATUS          current
      DESCRIPTION
          "The number of entries in the DomainNames table."
      DEFVAL { 0 }
      ::= { arrisRouterBSSPasspointEntry 7 }

arrisRouterBssPasspoint3GPPNetworks  OBJECT-TYPE
      SYNTAX      INTEGER(0..10)
      MAX-ACCESS      read-write
      STATUS          current
      DESCRIPTION
          "The number of entries in the 3GPPNetworks table."
      DEFVAL { 0 }
      ::= { arrisRouterBSSPasspointEntry 8 }

arrisRouterBssPasspointNAIRealmsCount  OBJECT-TYPE
      SYNTAX      INTEGER(0..10)
      MAX-ACCESS      read-write
      STATUS          current
      DESCRIPTION
          "The number of entries in the NAIRealms table."
      DEFVAL { 0 }
      ::= { arrisRouterBSSPasspointEntry 9 }

arrisRouterBssPasspointIPAddressAvailability OBJECT-TYPE
      SYNTAX      INTEGER(0..58)
      MAX-ACCESS      read-write
      STATUS          current
      DESCRIPTION
          "IP address availability value"
      ::= { arrisRouterBSSPasspointEntry 10 }

----------------------------------------------------------------------------------------
-- Passpoint BSS Venu Names Table
----------------------------------------------------------------------------------------
arrisRouterBSSPasspointVenuNamesTable OBJECT-TYPE
      SYNTAX          SEQUENCE OF ArrisRouterBSSPasspointVenuNamesEntry
      MAX-ACCESS      not-accessible
      STATUS          current
      DESCRIPTION
          "A table of Venue Names where the access point is installed."
      ::= { arrisRouterBssPasspoint 11 }

arrisRouterBSSPasspointVenuNamesEntry OBJECT-TYPE
      SYNTAX          ArrisRouterBSSPasspointVenuNamesEntry
      MAX-ACCESS  not-accessible
      STATUS          current
      DESCRIPTION
          ""
      INDEX { ifIndex,  arrisRouterBssPasspointVenuNamesTableIndex }
      ::= { arrisRouterBSSPasspointVenuNamesTable 1 }

ArrisRouterBSSPasspointVenuNamesEntry ::=
        SEQUENCE        {
        arrisRouterBssPasspointVenuNamesTableIndex         INTEGER,
        arrisRouterBssPasspointVenuNamesLanguageCode       OCTET STRING,
        arrisRouterBssPasspointVenuNamesVenuName           OCTET STRING
        }

arrisRouterBssPasspointVenuNamesTableIndex OBJECT-TYPE
      SYNTAX      INTEGER(1..10)
      MAX-ACCESS  not-accessible
      STATUS      current
      DESCRIPTION
          "Index used to order the Venu Names Entries.  Max 10 allowed per BSS"
      ::= { arrisRouterBSSPasspointVenuNamesEntry 1 }

arrisRouterBssPasspointVenuNamesLanguageCode  OBJECT-TYPE
      SYNTAX      OCTET STRING(SIZE(2..3))
      MAX-ACCESS  read-write
      STATUS      current
      DESCRIPTION
          "A 2 or 3 octet ISO-14962-1997 encoded string field that defines the language
          used in the Venue Name field. The code value is selected from ISO-639."
      DEFVAL { "eng" }
      ::= { arrisRouterBSSPasspointVenuNamesEntry 2 }

arrisRouterBssPasspointVenuNamesVenuName  OBJECT-TYPE
      SYNTAX      OCTET STRING(SIZE(0..504))
      MAX-ACCESS  read-write
      STATUS      current
      DESCRIPTION
          "Indicates the Venue Name where the access point is installed. This additional
          meta data about the venue is included in the Venue Name ANQP-element. This
          parameter accepts UTF-8 encoded string represented as hexBinary string."
      DEFVAL { "" }
      ::= { arrisRouterBSSPasspointVenuNamesEntry 3 }

----------------------------------------------------------------------------------------
-- Passpoint BSS Operator Names Table
----------------------------------------------------------------------------------------
arrisRouterBSSPasspointOperatorNamesTable OBJECT-TYPE
      SYNTAX          SEQUENCE OF ArrisRouterBSSPasspointOperatorNamesEntry
      MAX-ACCESS      not-accessible
      STATUS          current
      DESCRIPTION
          "A table of Operator Friendly Names of the entity operating the IEEE 802.11
          access network i.e. the Hotspot Operator."
      ::= { arrisRouterBssPasspoint 12 }

arrisRouterBSSPasspointOperatorNamesEntry OBJECT-TYPE
      SYNTAX          ArrisRouterBSSPasspointOperatorNamesEntry
      MAX-ACCESS  not-accessible
      STATUS          current
      DESCRIPTION
          ""
      INDEX { ifIndex }
      ::= { arrisRouterBSSPasspointOperatorNamesTable 1 }

ArrisRouterBSSPasspointOperatorNamesEntry ::=
        SEQUENCE        {
        arrisRouterBssPasspointOperatorNamesTableIndex         INTEGER,
        arrisRouterBssPasspointOperatorNamesLanguageCode       OCTET STRING,
        arrisRouterBssPasspointOperatorNamesOperatorName       OCTET STRING
        }

arrisRouterBssPasspointOperatorNamesTableIndex OBJECT-TYPE
      SYNTAX      INTEGER(1..10)
      MAX-ACCESS  not-accessible
      STATUS      current
      DESCRIPTION
          "Index used to order the Operator Names Entries.  Max 10 allowed per BSS"
      ::= { arrisRouterBSSPasspointOperatorNamesEntry 1 }

arrisRouterBssPasspointOperatorNamesLanguageCode  OBJECT-TYPE
      SYNTAX      OCTET STRING(SIZE(1..64))
      MAX-ACCESS  read-write
      STATUS      current
      DESCRIPTION
          "A 2 or 3 octet ISO-14962-1997 encoded string field that defines the language
          used in the Venue Name field. The code value is selected from ISO-639."
      DEFVAL { "eng" }
      ::= { arrisRouterBSSPasspointOperatorNamesEntry 2 }

arrisRouterBssPasspointOperatorNamesOperatorName  OBJECT-TYPE
      SYNTAX      OCTET STRING(SIZE(0..504))
      MAX-ACCESS  read-write
      STATUS      current
      DESCRIPTION
          "Indicates the Operator Friendly Name of the entity operating the IEEE 802.11 AN
          i.e. the Hotspot Operator. This parameter accepts UTF-8 encoded string
          represented as hexBinary string."
      DEFVAL { "" }
      ::= { arrisRouterBSSPasspointOperatorNamesEntry 3 }

----------------------------------------------------------------------------------------
-- Passpoint BSS Consortium OIs (Organizational Identifiers) Table
----------------------------------------------------------------------------------------
arrisRouterBSSPasspointConsortiumOIsTable OBJECT-TYPE
      SYNTAX          SEQUENCE OF ArrisRouterBSSPasspointConsortiumOIsEntry
      MAX-ACCESS      not-accessible
      STATUS          current
      DESCRIPTION
          "A table of Consortium OIs (Organization Identifiers) which are to be transmitted
          in an ANQP Roaming Consortium ANQP-element. Each entry of this table corresponds
          to a roaming consortium or single SSP. The first three entries of this table are
          transmitted in Beacon and Probe Response frames."
      ::= { arrisRouterBssPasspoint 13 }

arrisRouterBSSPasspointConsortiumOIsEntry OBJECT-TYPE
      SYNTAX          ArrisRouterBSSPasspointConsortiumOIsEntry
      MAX-ACCESS  not-accessible
      STATUS          current
      DESCRIPTION
          ""
      INDEX { ifIndex,  arrisRouterBssPasspointConsortiumOIsTableIndex }
      ::= { arrisRouterBSSPasspointConsortiumOIsTable 1 }

ArrisRouterBSSPasspointConsortiumOIsEntry ::=
        SEQUENCE        {
        arrisRouterBssPasspointConsortiumOIsTableIndex         INTEGER,
        arrisRouterBssPasspointConsortiumOIsOI                 OCTET STRING
        }

arrisRouterBssPasspointConsortiumOIsTableIndex OBJECT-TYPE
      SYNTAX      INTEGER(1..10)
      MAX-ACCESS  not-accessible
      STATUS      current
      DESCRIPTION
          "Index used to order the Consortium OI Entries.  Max 10 allowed per BSS"
      ::= { arrisRouterBSSPasspointConsortiumOIsEntry 1 }

arrisRouterBssPasspointConsortiumOIsOI  OBJECT-TYPE
      SYNTAX      OCTET STRING(SIZE(0..16))
      MAX-ACCESS  read-write
      STATUS      current
      DESCRIPTION
          "A IEEE defined public organizationally unique identifier (OUI-24 or OUI-36)."
      ::= { arrisRouterBSSPasspointConsortiumOIsEntry 2 }

----------------------------------------------------------------------------------------
-- Passpoint BSS Domain Names Table
----------------------------------------------------------------------------------------
arrisRouterBSSPasspointDomainNamesTable OBJECT-TYPE
      SYNTAX          SEQUENCE OF ArrisRouterBSSPasspointDomainNamesEntry
      MAX-ACCESS      not-accessible
      STATUS          current
      DESCRIPTION
          "A table of Domain Names of the entity operating the IEEE 802.11 access network."
      ::= { arrisRouterBssPasspoint 14 }

arrisRouterBSSPasspointDomainNamesEntry OBJECT-TYPE
      SYNTAX          ArrisRouterBSSPasspointDomainNamesEntry
      MAX-ACCESS  not-accessible
      STATUS          current
      DESCRIPTION
          ""
      INDEX { ifIndex,  arrisRouterBssPasspointDomainNamesTableIndex }
      ::= { arrisRouterBSSPasspointDomainNamesTable 1 }

ArrisRouterBSSPasspointDomainNamesEntry ::=
        SEQUENCE        {
        arrisRouterBssPasspointDomainNamesTableIndex         INTEGER,
        arrisRouterBssPasspointDomainNamesDomainName         DisplayString
        }

arrisRouterBssPasspointDomainNamesTableIndex OBJECT-TYPE
      SYNTAX      INTEGER(1..10)
      MAX-ACCESS  not-accessible
      STATUS      current
      DESCRIPTION
          "Index used to order the Domain Name Entries.  Max 10 allowed per BSS"
      ::= { arrisRouterBSSPasspointDomainNamesEntry 1 }

arrisRouterBssPasspointDomainNamesDomainName  OBJECT-TYPE
      SYNTAX      DisplayString(SIZE(0..255))
      MAX-ACCESS  read-write
      STATUS      current
      DESCRIPTION
          "Domain Name of the entity operating the IEEE 802.11 access network that is
          compliant with the 'Preferred Name Syntax' as defined in IETF RFC 1035. This
          field is included in the Domain Name ANQP-element and is common across access
          points of an area that are part of the same Extended Service Set (ESS)."
      DEFVAL { "" }
      ::= { arrisRouterBSSPasspointDomainNamesEntry 2 }

----------------------------------------------------------------------------------------
-- Passpoint BSS 3GPP Networks Table
----------------------------------------------------------------------------------------
arrisRouterBSSPasspoint3GPPNetworksTable OBJECT-TYPE
      SYNTAX          SEQUENCE OF ArrisRouterBSSPasspoint3GPPNetworksEntry
      MAX-ACCESS      not-accessible
      STATUS          current
      DESCRIPTION
          "A table of Domain Names of the entity operating the IEEE 802.11 access network."
      ::= { arrisRouterBssPasspoint 15 }

arrisRouterBSSPasspoint3GPPNetworksEntry OBJECT-TYPE
      SYNTAX          ArrisRouterBSSPasspoint3GPPNetworksEntry
      MAX-ACCESS  not-accessible
      STATUS          current
      DESCRIPTION
          ""
      INDEX { ifIndex,  arrisRouterBssPasspoint3GPPNetworksTableIndex }
      ::= { arrisRouterBSSPasspoint3GPPNetworksTable 1 }

ArrisRouterBSSPasspoint3GPPNetworksEntry ::=
        SEQUENCE        {
        arrisRouterBssPasspoint3GPPNetworksTableIndex         INTEGER,
        arrisRouterBssPasspoint3GPPNetworksMCC                DisplayString,
        arrisRouterBssPasspoint3GPPNetworksMNC                DisplayString
        }

arrisRouterBssPasspoint3GPPNetworksTableIndex OBJECT-TYPE
      SYNTAX      INTEGER(1..10)
      MAX-ACCESS  not-accessible
      STATUS      current
      DESCRIPTION
          "Index used to order the 3GPP Network Entries. Max 10 allowed per BSS"
      ::= { arrisRouterBSSPasspoint3GPPNetworksEntry 1 }

arrisRouterBssPasspoint3GPPNetworksMCC  OBJECT-TYPE
      SYNTAX      DisplayString(SIZE(3))
      MAX-ACCESS  read-write
      STATUS      current
      DESCRIPTION
          "A 3 digit Mobile Country Code of the 3GPP Network."
      ::= { arrisRouterBSSPasspoint3GPPNetworksEntry 2 }

arrisRouterBssPasspoint3GPPNetworksMNC  OBJECT-TYPE
      SYNTAX      DisplayString(SIZE(2..3))
      MAX-ACCESS  read-write
      STATUS      current
      DESCRIPTION
          "A 2 or 3 digit Mobile Network Code of the 3GPP Network."
      ::= { arrisRouterBSSPasspoint3GPPNetworksEntry 3 }

----------------------------------------------------------------------------------------
-- Passpoint BSS NAI Realm Definition
----------------------------------------------------------------------------------------
arrisRouterBssPasspointNAIRealms OBJECT IDENTIFIER ::= { arrisRouterBssPasspoint 16 }

arrisRouterBSSPasspointNAIRealmsTable OBJECT-TYPE
      SYNTAX          SEQUENCE OF ArrisRouterBSSPasspointNAIRealmsEntry
      MAX-ACCESS      not-accessible
      STATUS          current
      DESCRIPTION
          "A table of Domain Names of the entity operating the IEEE 802.11 access network."
      ::= { arrisRouterBssPasspointNAIRealms 1 }

arrisRouterBSSPasspointNAIRealmsEntry OBJECT-TYPE
      SYNTAX          ArrisRouterBSSPasspointNAIRealmsEntry
      MAX-ACCESS  not-accessible
      STATUS          current
      DESCRIPTION
          ""
      INDEX { ifIndex,  arrisRouterBssPasspointNAIRealmsTableIndex }
      ::= { arrisRouterBSSPasspointNAIRealmsTable 1 }

ArrisRouterBSSPasspointNAIRealmsEntry ::=
        SEQUENCE        {
        arrisRouterBssPasspointNAIRealmsTableIndex         INTEGER,
        arrisRouterBssPasspointNAIRealmsEncodingType       INTEGER,
        arrisRouterBssPasspointNAIRealmsNAIRealm           DisplayString,
        arrisRouterBssPasspointNAIRealmsEAPMethodNoE       INTEGER
        }

arrisRouterBssPasspointNAIRealmsTableIndex OBJECT-TYPE
      SYNTAX      INTEGER(1..10)
      MAX-ACCESS  not-accessible
      STATUS      current
      DESCRIPTION
          "Index used to order the NAI Realms Entries.  Max 10 allowed per BSS"
      ::= { arrisRouterBSSPasspointNAIRealmsEntry 1 }

arrisRouterBssPasspointNAIRealmsEncodingType OBJECT-TYPE
      SYNTAX      INTEGER(0..1)
      MAX-ACCESS  read-write
      STATUS      current
      DESCRIPTION
          "Indicates NAI Realm Encoding Type used to encode NAI Realm ANQP Element. A
          value of 0 indicates that the NAI Realm in the NAI Realm subfield is formatted
          in accordance with IETF RFC4282. A value of 1 indicates that it is a UTF-8
          formatted character string."

      ::= { arrisRouterBSSPasspointNAIRealmsEntry 2 }

arrisRouterBssPasspointNAIRealmsNAIRealm  OBJECT-TYPE
      SYNTAX      DisplayString(SIZE(0..128))
      MAX-ACCESS  read-write
      STATUS      current
      DESCRIPTION
          "One or more NAI Realms delimited by a semi-colon character (ie ';')"
      DEFVAL { "" }
      ::= { arrisRouterBSSPasspointNAIRealmsEntry 3 }

arrisRouterBssPasspointNAIRealmsEAPMethodNoE OBJECT-TYPE
      SYNTAX      INTEGER(0..5)
      MAX-ACCESS  read-write
      STATUS      current
      DESCRIPTION
          "The number of entries in the EAPMethods table."
      DEFVAL { 0 }
      ::= { arrisRouterBSSPasspointNAIRealmsEntry 4 }

----------------------------------------------------------------------------------------
-- Passpoint BSS NAI Realm EAP Methods Definition
----------------------------------------------------------------------------------------
arrisRouterBSSPasspointNAIEAPMethodsTable OBJECT-TYPE
      SYNTAX          SEQUENCE OF ArrisRouterBSSPasspointNAIEAPMethodsEntry
      MAX-ACCESS      not-accessible
      STATUS          current
      DESCRIPTION
          "A table of EAP Methods that each NAI Realm supports."
      ::= { arrisRouterBssPasspointNAIRealms 2 }

arrisRouterBSSPasspointNAIEAPMethodsEntry OBJECT-TYPE
      SYNTAX          ArrisRouterBSSPasspointNAIEAPMethodsEntry
      MAX-ACCESS  not-accessible
      STATUS          current
      DESCRIPTION
          ""
      INDEX { ifIndex, arrisRouterBssPasspointNAIRealmsTableIndex,
              arrisRouterBssPasspointNAIEAPMethodsTableIndex }
      ::= { arrisRouterBSSPasspointNAIEAPMethodsTable 1 }

ArrisRouterBSSPasspointNAIEAPMethodsEntry ::=
        SEQUENCE        {
        arrisRouterBssPasspointNAIEAPMethodsTableIndex            INTEGER,
        arrisRouterBssPasspointNAIEAPMethodsEAPMethod             DisplayString,
        arrisRouterBssPasspointNAIEAPMethodsAuthParamsEntries     INTEGER
        }

arrisRouterBssPasspointNAIEAPMethodsTableIndex OBJECT-TYPE
      SYNTAX      INTEGER(0..5)
      MAX-ACCESS  not-accessible
      STATUS      current
      DESCRIPTION
          "Index used to order the NAI Realms EAP Methods Entries.  Max 5 allowed per
          NAI Realm."
      ::= { arrisRouterBSSPasspointNAIEAPMethodsEntry 1 }

arrisRouterBssPasspointNAIEAPMethodsEAPMethod OBJECT-TYPE
      SYNTAX      DisplayString(SIZE(0..16))
      MAX-ACCESS  read-write
      STATUS      current
      DESCRIPTION
          "EAP Method type that the NAI Realm supports. Enumeration of:
           0 = None
           13 = EAP-TLS
           21 = EAP-TTLS
           25 = PEAP
           29 = EAP-MSCHAP-V2

           The list is based on IANA EAP Method Type Numbers published at:
           http://www.iana.org/assignments/eap-numbers/eap-numbers.xhtml"
      ::= { arrisRouterBSSPasspointNAIEAPMethodsEntry 2 }

arrisRouterBssPasspointNAIEAPMethodsAuthParamsEntries OBJECT-TYPE
      SYNTAX      INTEGER(0..4)
      MAX-ACCESS  read-write
      STATUS      current
      DESCRIPTION
          "The number of entries in the AuthenticationParameters table."
      DEFVAL { 0 }
      ::= { arrisRouterBSSPasspointNAIEAPMethodsEntry 3 }

----------------------------------------------------------------------------------------
-- Passpoint BSS NAI Realm EAP Method Authentication Parameters Definitions
----------------------------------------------------------------------------------------
arrisRouterBSSPasspointNAIEAPAuthParamsTable OBJECT-TYPE
      SYNTAX          SEQUENCE OF ArrisRouterBSSPasspointNAIEAPAuthParamsEntry
      MAX-ACCESS      not-accessible
      STATUS          current
      DESCRIPTION
          "A table of Authentication Parameters associated with each NAI EAP Method entry."
      ::= { arrisRouterBssPasspointNAIRealms 3 }

arrisRouterBSSPasspointNAIEAPAuthParamsEntry OBJECT-TYPE
      SYNTAX          ArrisRouterBSSPasspointNAIEAPAuthParamsEntry
      MAX-ACCESS  not-accessible
      STATUS          current
      DESCRIPTION
          ""
      INDEX { ifIndex,  arrisRouterBssPasspointNAIRealmsTableIndex,
              arrisRouterBssPasspointNAIEAPMethodsTableIndex,
              arrisRouterBssPasspointNAIEAPAuthParamsTableIndex
           }
      ::= { arrisRouterBSSPasspointNAIEAPAuthParamsTable 1 }

ArrisRouterBSSPasspointNAIEAPAuthParamsEntry ::=
        SEQUENCE        {
        arrisRouterBssPasspointNAIEAPAuthParamsTableIndex          INTEGER,
        arrisRouterBssPasspointNAIEAPAuthParamsID                  INTEGER,
        arrisRouterBssPasspointNAIEAPAuthParamsValue               OCTET STRING
        }

arrisRouterBssPasspointNAIEAPAuthParamsTableIndex OBJECT-TYPE
      SYNTAX      INTEGER(1..4)
      MAX-ACCESS  not-accessible
      STATUS      current
      DESCRIPTION
          "Index used to order the NAI Realms EAP Methods Authentication Parameters Entries"
      ::= { arrisRouterBSSPasspointNAIEAPAuthParamsEntry 1 }

arrisRouterBssPasspointNAIEAPAuthParamsID OBJECT-TYPE
      SYNTAX      INTEGER(0..255)
      MAX-ACCESS  read-write
      STATUS      current
      DESCRIPTION
          "ID indicates different types of information and is based on IEEE 802.11-2012
          Table 8-188.

          0 - Reserved
          1 - Expanded EAP Method
          2 - Non-EAP Inner Authentication Type
          3 - Inner Authentication EAP Method Type
          4 - Expanded Inner EAP Method
          5 - Credential Type
          6 - Tunneled EAP Method Credential Type
          221 - Vendor Specific
          All other values are reserved"
      ::= { arrisRouterBSSPasspointNAIEAPAuthParamsEntry 2 }

arrisRouterBssPasspointNAIEAPAuthParamsValue OBJECT-TYPE
      SYNTAX      OCTET STRING(SIZE(0..255))
      MAX-ACCESS  read-write
      STATUS      current
      DESCRIPTION
          "Value encoded in hexBinary (octet string) format as per the section 8.4.4.10
          of IEEE 802.11-2012 specification."
      ::= { arrisRouterBSSPasspointNAIEAPAuthParamsEntry 3 }

----------------------------------------------------------------------------------------
-- Passpoint BSS WAN Metrics Table
----------------------------------------------------------------------------------------
arrisRouterBSSPasspointWANMetricsTable OBJECT-TYPE
      SYNTAX          SEQUENCE OF ArrisRouterBSSPasspointWANMetricsEntry
      MAX-ACCESS      not-accessible
      STATUS          current
      DESCRIPTION
          "A table of Domain Names of the entity operating the IEEE 802.11 access network."
      ::= { arrisRouterBssPasspoint 17 }

arrisRouterBSSPasspointWANMetricsEntry OBJECT-TYPE
      SYNTAX          ArrisRouterBSSPasspointWANMetricsEntry
      MAX-ACCESS  not-accessible
      STATUS          current
      DESCRIPTION
          ""
      INDEX { ifIndex }
      ::= { arrisRouterBSSPasspointWANMetricsTable 1 }

ArrisRouterBSSPasspointWANMetricsEntry ::=
        SEQUENCE        {
        arrisRouterBssPasspointWANMetricsLinkStatus            DisplayString,
        arrisRouterBssPasspointWANMetricsAirCapacity           TruthValue,
        arrisRouterBssPasspointWANMetricsDownlinkSpeed         Unsigned32,
        arrisRouterBssPasspointWANMetricsUplinkSpeed           Unsigned32,
        arrisRouterBssPasspointWANMetricsDownlinkLoad          INTEGER,
        arrisRouterBssPasspointWANMetricsUplinkLoad            INTEGER
        }

arrisRouterBssPasspointWANMetricsLinkStatus OBJECT-TYPE
      SYNTAX      DisplayString(SIZE(6..8))
      MAX-ACCESS  read-write
      STATUS      current
      DESCRIPTION
          "Reflects the status of the WAN Link. Enumeration of:
           0 = Reserved
           1 = LinkUp
           2 = LinkDown
           3 = LinkTest
          "
      ::= { arrisRouterBSSPasspointWANMetricsEntry 1 }

arrisRouterBssPasspointWANMetricsAirCapacity OBJECT-TYPE
      SYNTAX      TruthValue
      MAX-ACCESS  read-write
      STATUS      current
      DESCRIPTION
          "Set to true if the WAN link is at capacity and no additional mobile devices
          will be permitted to associate to the AP. Otherwise false."
      ::= { arrisRouterBSSPasspointWANMetricsEntry 2 }

arrisRouterBssPasspointWANMetricsDownlinkSpeed OBJECT-TYPE
      SYNTAX      Unsigned32(0..4294967295)
      MAX-ACCESS  read-write
      STATUS      current
      DESCRIPTION
          "An estimate of the WAN backhaul link's current downlink speed in kilobits per
          second (kbps). The maximum value of this field is 4,294,967,296 kbps
          (approx. 4.2Tbps)."
      ::= { arrisRouterBSSPasspointWANMetricsEntry 3 }

arrisRouterBssPasspointWANMetricsUplinkSpeed OBJECT-TYPE
      SYNTAX      Unsigned32(0..4294967295)
      MAX-ACCESS  read-write
      STATUS      current
      DESCRIPTION
          "An estimate of the WAN backhaul link's current uplink speed in kilobits per
          second (kbps). The maximum value of this field is 4,294,967,296 kbps
          (approx. 4.2Tbps)."
      ::= { arrisRouterBSSPasspointWANMetricsEntry 4 }

arrisRouterBssPasspointWANMetricsDownlinkLoad OBJECT-TYPE
      SYNTAX      INTEGER(0..100)
      MAX-ACCESS  read-write
      STATUS      current
      DESCRIPTION
          "Current percentage % loading of the downlink WAN connection."
      ::= { arrisRouterBSSPasspointWANMetricsEntry 5 }

arrisRouterBssPasspointWANMetricsUplinkLoad OBJECT-TYPE
      SYNTAX      INTEGER(0..100)
      MAX-ACCESS  read-write
      STATUS      current
      DESCRIPTION
          "Current percentage % loading of the uplink WAN connection."
      ::= { arrisRouterBSSPasspointWANMetricsEntry 6 }

----------------------------------------------------------------------------------------
-- Per BSS Passpoint Online Sign Up (OSU) Service Configuration
----------------------------------------------------------------------------------------
arrisRouterBssPasspointOSUProviders OBJECT IDENTIFIER ::= { arrisRouterBssPasspoint 18 }

arrisRouterBSSPasspointOSUTable OBJECT-TYPE
      SYNTAX          SEQUENCE OF ArrisRouterBSSPasspointOSUEntry
      MAX-ACCESS      not-accessible
      STATUS          current
      DESCRIPTION
          "Tables Providing counts (Per BSS) regarding the Online Sign Up (OSU) Service
          that is advertised via OSU Provider List element in beacon and probe frames.
          Refer section 4.8 of WFA HS2.0."
      ::= { arrisRouterBssPasspointOSUProviders 1 }

arrisRouterBSSPasspointOSUEntry OBJECT-TYPE
      SYNTAX          ArrisRouterBSSPasspointOSUEntry
      MAX-ACCESS  not-accessible
      STATUS          current
      DESCRIPTION
          ""
      INDEX { ifIndex }
      ::= { arrisRouterBSSPasspointOSUTable 1 }

ArrisRouterBSSPasspointOSUEntry ::=
       SEQUENCE        {
        arrisRouterBssPasspointOSUNumberEntries           INTEGER
        }

arrisRouterBssPasspointOSUNumberEntries OBJECT-TYPE
      SYNTAX      INTEGER(0..4)
      MAX-ACCESS  read-write
      STATUS      current
      DESCRIPTION
          "The number of entries in the OSUProviders table."
      DEFVAL { 0 }
      ::= { arrisRouterBSSPasspointOSUEntry 1 }

----------------------------------------------------------------------------------------
-- Per BSS Passpoint Online Sign Up (OSU) Providers Configuration Tables
----------------------------------------------------------------------------------------
arrisRouterBSSPasspointOSUProvidersTable OBJECT-TYPE
      SYNTAX          SEQUENCE OF ArrisRouterBSSPasspointOSUProvidersEntry
      MAX-ACCESS      not-accessible
      STATUS          current
      DESCRIPTION
          "A table of OSU Providers offering Online Sign Up service. This table is included
          in the OSU Provider sub-field in the OSU Provider List element."
      ::= { arrisRouterBssPasspointOSUProviders 2 }

arrisRouterBSSPasspointOSUProvidersEntry OBJECT-TYPE
      SYNTAX          ArrisRouterBSSPasspointOSUProvidersEntry
      MAX-ACCESS  not-accessible
      STATUS          current
      DESCRIPTION
          ""
      INDEX { ifIndex, arrisRouterBssPasspointOSUProvidersTableIndex }
      ::= { arrisRouterBSSPasspointOSUProvidersTable 1 }

ArrisRouterBSSPasspointOSUProvidersEntry ::=
        SEQUENCE        {
        arrisRouterBssPasspointOSUProvidersTableIndex          INTEGER,
        arrisRouterBssPasspointOSUProvidersServerURI           DisplayString,
        arrisRouterBssPasspointOSUProvidersMethodsList         DisplayString,
        arrisRouterBssPasspointOSUProvidersOSUNAI              DisplayString,
        arrisRouterBssPasspointOSUProvidersNamesNoE            INTEGER,
        arrisRouterBssPasspointOSUProvidersIconsNoE            INTEGER,
        arrisRouterBssPasspointOSUProvidersSvcDescrNoE         INTEGER
        }

arrisRouterBssPasspointOSUProvidersTableIndex OBJECT-TYPE
      SYNTAX      INTEGER (1..4)
      MAX-ACCESS  not-accessible
      STATUS      current
      DESCRIPTION
          "Index used to order the OSU Providers Entries"
      ::= { arrisRouterBSSPasspointOSUProvidersEntry 1 }

arrisRouterBssPasspointOSUProvidersServerURI OBJECT-TYPE
      SYNTAX      DisplayString(SIZE(1..255))
      MAX-ACCESS  read-write
      STATUS      current
      DESCRIPTION
          "The URI of the OSU Server that is used for OSU with the Service Provider
          indicated in the Names table. It is formatted in accordance with the IETF RFC 3986."
      ::= { arrisRouterBSSPasspointOSUProvidersEntry 2 }

arrisRouterBssPasspointOSUProvidersMethodsList OBJECT-TYPE
      SYNTAX      DisplayString(SIZE(1..16))
      MAX-ACCESS  read-write
      STATUS      current
      DESCRIPTION
          "A comma seperated list of OSU Method values represented as integers. The methods
          are listed in the ServiceProvider's preferred order with the most-preferred method
          first. Possible values (integers) are selected from Table 10 of WFA HS2.0.

          0 - OMA-DM
          1 - SOAP-XML SPP
          All other values (2 - 255) are reserved. Example value '0,1' without quotes."
      ::= { arrisRouterBSSPasspointOSUProvidersEntry 3 }

arrisRouterBssPasspointOSUProvidersOSUNAI OBJECT-TYPE
      SYNTAX      DisplayString(SIZE(1..72))
      MAX-ACCESS  read-write
      STATUS      current
      DESCRIPTION
          "Contains the NAI that is used for OSU with the ServiceProvider indicated in the
          Names table. OSUNAI is formatted in accordance with IETF RFC 4282."
      DEFVAL { "" }
      ::= { arrisRouterBSSPasspointOSUProvidersEntry 4 }

arrisRouterBssPasspointOSUProvidersNamesNoE OBJECT-TYPE
      SYNTAX      INTEGER(0..4)
      MAX-ACCESS  read-write
      STATUS      current
      DESCRIPTION
          "The number of entries in the Names table."
      DEFVAL { 0 }
      ::= { arrisRouterBSSPasspointOSUProvidersEntry 5 }

arrisRouterBssPasspointOSUProvidersIconsNoE OBJECT-TYPE
      SYNTAX      INTEGER(0..4)
      MAX-ACCESS  read-write
      STATUS      current
      DESCRIPTION
          "The number of entries in the Icons table."
      DEFVAL { 0 }
      ::= { arrisRouterBSSPasspointOSUProvidersEntry 6 }

arrisRouterBssPasspointOSUProvidersSvcDescrNoE OBJECT-TYPE
      SYNTAX      INTEGER(0..4)
      MAX-ACCESS  read-write
      STATUS      current
      DESCRIPTION
          "The number of entries in the Icons table."
      DEFVAL { 0 }
      ::= { arrisRouterBSSPasspointOSUProvidersEntry 7 }

----------------------------------------------------------------------------------------
-- Per BSS Passpoint Online Sign Up (OSU) Providers Names Tables
----------------------------------------------------------------------------------------
arrisRouterBSSPasspointOSUProvidersNamesTable OBJECT-TYPE
      SYNTAX         SEQUENCE OF ArrisRouterBSSPasspointOSUProvidersNamesEntry
      MAX-ACCESS     not-accessible
      STATUS         current
      DESCRIPTION
          "A table of OSU Providers Friendly Names that are included in the OSU Provider
          List element."
      ::= { arrisRouterBssPasspointOSUProviders 3 }

arrisRouterBSSPasspointOSUProvidersNamesEntry OBJECT-TYPE
      SYNTAX         ArrisRouterBSSPasspointOSUProvidersNamesEntry
      MAX-ACCESS  not-accessible
      STATUS         current
      DESCRIPTION
          ""
      INDEX { ifIndex, arrisRouterBssPasspointOSUProvidersTableIndex,
             arrisRouterBssPasspointOSUProvidersNamesTableIndex }
      ::= { arrisRouterBSSPasspointOSUProvidersNamesTable 1 }

ArrisRouterBSSPasspointOSUProvidersNamesEntry ::=
         SEQUENCE       {
        arrisRouterBssPasspointOSUProvidersNamesTableIndex         INTEGER,
        arrisRouterBssPasspointOSUProvidersNamesLanguageCode       DisplayString,
        arrisRouterBssPasspointOSUProvidersNamesFriendlyName       OCTET STRING
        }

arrisRouterBssPasspointOSUProvidersNamesTableIndex OBJECT-TYPE
      SYNTAX      INTEGER(1..4)
      MAX-ACCESS  not-accessible
      STATUS      current
      DESCRIPTION
          "Index used to order the OSU Providers Names Entries"
      ::= { arrisRouterBSSPasspointOSUProvidersNamesEntry 1 }

arrisRouterBssPasspointOSUProvidersNamesLanguageCode OBJECT-TYPE
      SYNTAX      DisplayString(SIZE(1..3))
      MAX-ACCESS  read-write
      STATUS      current
      DESCRIPTION
          "A 2 or 3 octet ISO-14962-1997 encoded string field that defines the language
          used in the OSU Provider Friendly Name field. The code value is selected from ISO-639."
      DEFVAL { "eng" }
      ::= { arrisRouterBSSPasspointOSUProvidersNamesEntry 2 }

arrisRouterBssPasspointOSUProvidersNamesFriendlyName OBJECT-TYPE
      SYNTAX      OCTET STRING(SIZE(0..504))
      MAX-ACCESS  read-write
      STATUS      current
      DESCRIPTION
          "Indicates the UTF-8 encoded (represented as hexBinary) OSU Provider Friendly
          Name in the human language identified by the language code. This parameter accepts
          UTF-8 encoded string represented as hexBinary string."
      DEFVAL { "" }
      ::= { arrisRouterBSSPasspointOSUProvidersNamesEntry 3 }

----------------------------------------------------------------------------------------
-- Per BSS Passpoint Online Sign Up (OSU) Providers Icon Tables
----------------------------------------------------------------------------------------
arrisRouterBSSPasspointOSUProvidersIconsTable OBJECT-TYPE
      SYNTAX         SEQUENCE OF ArrisRouterBSSPasspointOSUProvidersIconsEntry
      MAX-ACCESS     not-accessible
      STATUS         current
      DESCRIPTION
          "A table of Icons that are included in the Icons Available subfield of the OSU
          Provider List element. The Icons Available subfield provides metadata about the
          OSU provider icon file(s) available for download. The Icons Available subfield
          provides metadata for zero or more OSU Provider icons; if more than one Icon
          Metadata subfield is present, each icon so represented provides the same image
          in a different image size."
      ::= { arrisRouterBssPasspointOSUProviders 4 }

arrisRouterBSSPasspointOSUProvidersIconsEntry OBJECT-TYPE
      SYNTAX         ArrisRouterBSSPasspointOSUProvidersIconsEntry
      MAX-ACCESS  not-accessible
      STATUS         current
      DESCRIPTION
          ""
      INDEX { ifIndex, arrisRouterBssPasspointOSUProvidersTableIndex,
             arrisRouterBssPasspointOSUProvidersIconsTableIndex }
      ::= { arrisRouterBSSPasspointOSUProvidersIconsTable 1 }

ArrisRouterBSSPasspointOSUProvidersIconsEntry ::=
         SEQUENCE       {
        arrisRouterBssPasspointOSUProvidersIconsTableIndex         INTEGER,
        arrisRouterBssPasspointOSUProvidersIconsIconWidth          INTEGER,
        arrisRouterBssPasspointOSUProvidersIconsIconHeight         INTEGER,
        arrisRouterBssPasspointOSUProvidersIconsLanguageCode       DisplayString,
        arrisRouterBssPasspointOSUProvidersIconsIconType           DisplayString,
        arrisRouterBssPasspointOSUProvidersIconsIconFileName       OCTET STRING
        }

arrisRouterBssPasspointOSUProvidersIconsTableIndex OBJECT-TYPE
      SYNTAX      INTEGER(1..4)
      MAX-ACCESS  not-accessible
      STATUS      current
      DESCRIPTION
          "Index used to order the OSU Providers Icon Entries"
      ::= { arrisRouterBSSPasspointOSUProvidersIconsEntry 1 }

arrisRouterBssPasspointOSUProvidersIconsIconWidth OBJECT-TYPE
      SYNTAX      INTEGER(0..65535)
      MAX-ACCESS  read-write
      STATUS      current
      DESCRIPTION
          "Width in pixel of the OSU Provider icon named by the IconFilename."
      ::= { arrisRouterBSSPasspointOSUProvidersIconsEntry 2 }

arrisRouterBssPasspointOSUProvidersIconsIconHeight OBJECT-TYPE
      SYNTAX      INTEGER(0..65535)
      MAX-ACCESS  read-write
      STATUS      current
      DESCRIPTION
          "Height in pixel of the OSU Provider icon named by the IconFilename."
      ::= { arrisRouterBSSPasspointOSUProvidersIconsEntry 3 }

arrisRouterBssPasspointOSUProvidersIconsLanguageCode OBJECT-TYPE
      SYNTAX      DisplayString(SIZE(1..3))
      MAX-ACCESS  read-write
      STATUS      current
      DESCRIPTION
          "A 2 or 3 octet ISO-14962-1997 encoded string field that defines the language
          used in the Icon file if any. The code value is selected from ISO-639. If there
          is no linguistic content to the icon/logo, the LanguageCode is set to 'zxx'."
      DEFVAL { "zxx" }
      ::= { arrisRouterBSSPasspointOSUProvidersIconsEntry 4 }

arrisRouterBssPasspointOSUProvidersIconsIconType OBJECT-TYPE
      SYNTAX      DisplayString(SIZE(0..128))
      MAX-ACCESS  read-write
      STATUS      current
      DESCRIPTION
          "The IconType is the MIME media type of the binary icon file named by the IconFilename.
          The IconType field is formatted in accordance with RFC-4288 and its value is selected
          from the IANA MIME Media Types registered at
          http://www.iana.org/assignments/media-types/index.html"
      ::= { arrisRouterBSSPasspointOSUProvidersIconsEntry 5 }

arrisRouterBssPasspointOSUProvidersIconsIconFileName OBJECT-TYPE
      SYNTAX      OCTET STRING(SIZE(0..255))
      MAX-ACCESS  read-write
      STATUS      current
      DESCRIPTION
          "The IconFilename is a UTF-8 encoded field whose value contains the filename of
          the Icon having the metadata provided in this icon instance."
      DEFVAL { "" }
      ::= { arrisRouterBSSPasspointOSUProvidersIconsEntry 6 }

----------------------------------------------------------------------------------------
-- Per BSS Passpoint Online Sign Up (OSU) Providers Service Description Table
----------------------------------------------------------------------------------------
arrisRouterBSSPasspointOSUProvidersSvcDescrTable OBJECT-TYPE
      SYNTAX         SEQUENCE OF ArrisRouterBSSPasspointOSUProvidersSvcDescrEntry
      MAX-ACCESS     not-accessible
      STATUS         current
      DESCRIPTION
          "A table of OSU Service Descriptions that are included in the OSUServiceDescription
          subfield of the OSU Provider List element."
      ::= { arrisRouterBssPasspointOSUProviders 5 }

arrisRouterBSSPasspointOSUProvidersSvcDescrEntry OBJECT-TYPE
      SYNTAX         ArrisRouterBSSPasspointOSUProvidersSvcDescrEntry
      MAX-ACCESS  not-accessible
      STATUS         current
      DESCRIPTION
          ""
      INDEX { ifIndex, arrisRouterBssPasspointOSUProvidersTableIndex,
             arrisRouterBssPasspointOSUProvidersSvcDescrTableIndex }
      ::= { arrisRouterBSSPasspointOSUProvidersSvcDescrTable 1 }

ArrisRouterBSSPasspointOSUProvidersSvcDescrEntry ::=
         SEQUENCE       {
        arrisRouterBssPasspointOSUProvidersSvcDescrTableIndex         INTEGER,
        arrisRouterBssPasspointOSUProvidersSvcDescrLanguageCode       DisplayString,
        arrisRouterBssPasspointOSUProvidersSvcDescrSvcDescription     OCTET STRING
        }

arrisRouterBssPasspointOSUProvidersSvcDescrTableIndex OBJECT-TYPE
      SYNTAX      INTEGER(1..4)
      MAX-ACCESS  not-accessible
      STATUS      current
      DESCRIPTION
          "Index used to order the OSU Providers Icon Entries"
      ::= { arrisRouterBSSPasspointOSUProvidersSvcDescrEntry 1 }

arrisRouterBssPasspointOSUProvidersSvcDescrLanguageCode OBJECT-TYPE
      SYNTAX      DisplayString(SIZE(1..3))
      MAX-ACCESS  read-write
      STATUS      current
      DESCRIPTION
          "A 2 or 3 octet ISO-14962-1997 encoded string field that defines the language used in the OSU Provider Friendly Name field. The code value is selected from ISO-639."
      DEFVAL { "eng" }
      ::= { arrisRouterBSSPasspointOSUProvidersSvcDescrEntry 2 }

arrisRouterBssPasspointOSUProvidersSvcDescrSvcDescription OBJECT-TYPE
      SYNTAX      OCTET STRING(SIZE(0..504))
      MAX-ACCESS  read-write
      STATUS      current
      DESCRIPTION
          "Indicates the UTF-8 encoded (represented as hexBinary) string containing the
          ServiceProviders description of the service offering."
      DEFVAL { "" }
      ::= { arrisRouterBSSPasspointOSUProvidersSvcDescrEntry 3 }

-- ADD START, Task15083
arrisRouterAdvAirtimeCtrl OBJECT IDENTIFIER ::= { arrisRouterAirtimeCtrlCfg 100 }

arrisRouterAdvAirtimeRadioCtlTable OBJECT-TYPE
    	SYNTAX		SEQUENCE OF ArrisRouterAdvAirtimeRadioCtlEntry
    	MAX-ACCESS 	not-accessible
    	STATUS		current
    	DESCRIPTION
    		"This table assigns Advanced Airtime Fairness Parameters to a Radio."
    	::= { arrisRouterAdvAirtimeCtrl 1 }

arrisRouterAdvAirtimeRadioCtlEntry OBJECT-TYPE
	 SYNTAX		ArrisRouterAdvAirtimeRadioCtlEntry
	 MAX-ACCESS  not-accessible
	 STATUS		current
	 DESCRIPTION
		"A row in the table of the Advanced Airtime Management Control Table.
		ifIndex MUST be a RADIO INDEX "
     INDEX { ifIndex }	--from IF-MIB
	::= { arrisRouterAdvAirtimeRadioCtlTable 1 }

ArrisRouterAdvAirtimeRadioCtlEntry ::=
	 SEQUENCE	{
				  	arrisRouterAdvAirtimeRadioAlgorithmType             Unsigned32,
				  	arrisRouterAdvAirtimeRadioBSSWeightEnable           TruthValue,
				  	arrisRouterAdvAirtimeRadioSTAWeightEnable           TruthValue,
				  	arrisRouterAdvAirtimeRadioTrafficDirection          Unsigned32,
				  	arrisRouterAdvAirtimeRadioApplicationATMEnable      TruthValue
	}

arrisRouterAdvAirtimeRadioAlgorithmType OBJECT-TYPE
     SYNTAX		Unsigned32 (0..2)
     MAX-ACCESS	read-write
     STATUS		current
     DESCRIPTION
    	"Configuration of the Airtime Control for the Radio
    	    0 = Disabled
    	    1 = Global Fairness
    	    2 = Weighted Fairness
    	 "
     DEFVAL { 0 }
    ::= { arrisRouterAdvAirtimeRadioCtlEntry 1 }

arrisRouterAdvAirtimeRadioBSSWeightEnable OBJECT-TYPE
     SYNTAX		TruthValue
     MAX-ACCESS	read-write
     STATUS		current
     DESCRIPTION
    	 "Enables the BSS Weight Table ATM Feature for this radio as defined in the
    	 BSS Weight Tables."

     DEFVAL { false }
    ::= { arrisRouterAdvAirtimeRadioCtlEntry 2 }

arrisRouterAdvAirtimeRadioSTAWeightEnable OBJECT-TYPE
     SYNTAX		TruthValue
     MAX-ACCESS	read-write
     STATUS		current
     DESCRIPTION
    	 "Enables the STA Weight Table ATM Feature for this radio."

     DEFVAL { false }
    ::= { arrisRouterAdvAirtimeRadioCtlEntry 3 }

arrisRouterAdvAirtimeRadioTrafficDirection OBJECT-TYPE
     SYNTAX         Unsigned32 (1..3)
     MAX-ACCESS     read-write
     STATUS         current
     DESCRIPTION
                 "Defines the Fairness Direction the AP.
                        1 = Downlink (AP Tx)
                        2 = Uplink   (AP Rx)
                        3 = Uplink & Downlink
                  "
     DEFVAL { 1 }
    ::= { arrisRouterAdvAirtimeRadioCtlEntry 5 }

arrisRouterAdvAirtimeRadioApplicationATMEnable OBJECT-TYPE
     SYNTAX		TruthValue
     MAX-ACCESS	read-write
     STATUS		current
     DESCRIPTION
    	 "This parameter is used to enable or disable Application specific Airtime Management."

     DEFVAL { false }
    ::= { arrisRouterAdvAirtimeRadioCtlEntry 6 }

arrisRouterAdvAirtimeBSSWeight OBJECT IDENTIFIER ::= { arrisRouterAirtimeCtrlCfg 101 }

arrisRouterAdvAirtimeBSSWeightTable OBJECT-TYPE
    	SYNTAX		SEQUENCE OF ArrisRouterAdvAirtimeBSSWeightEntry
    	MAX-ACCESS 	not-accessible
    	STATUS		current
    	DESCRIPTION
    		"This table assigns Airtime Weights on a per BSS Basis."
    	::= { arrisRouterAdvAirtimeBSSWeight 1 }

arrisRouterAdvAirtimeBSSWeightEntry OBJECT-TYPE
	 SYNTAX		ArrisRouterAdvAirtimeBSSWeightEntry
	 MAX-ACCESS  not-accessible
	 STATUS		current
	 DESCRIPTION
		"A row in the table of the Advanced Airtime Management BSS Weight Table.
		ifIndex MUST be a BSS Index "
     INDEX { ifIndex }	--from IF-MIB
	::= { arrisRouterAdvAirtimeBSSWeightTable 1 }

ArrisRouterAdvAirtimeBSSWeightEntry ::=
     SEQUENCE	{
		  	        arrisRouterAdvAirtimeBSSDistributionType   Unsigned32,
		  	        arrisRouterAdvAirtimeBSSWeightValue        Unsigned32
		  	    }

arrisRouterAdvAirtimeBSSDistributionType OBJECT-TYPE
     SYNTAX		Unsigned32
     MAX-ACCESS	read-write
     STATUS		current
     DESCRIPTION
    	 "Define the method of airtime distribution for each BSS of each 802.11 band on
    	  the AP.
    	        0 = Dynamic Distribution
    	        1 = Strict Distribution
    	  "
     DEFVAL { 0 }
    ::= { arrisRouterAdvAirtimeBSSWeightEntry 1 }

arrisRouterAdvAirtimeBSSWeightValue OBJECT-TYPE
     SYNTAX		Unsigned32 (5..100)
     MAX-ACCESS	read-write
     STATUS		current
     DESCRIPTION "Sets the Percentage of Airtime to be allocated to this BSS.
                 Also allow 0 which means zero guaranteed airtime."
     ::= { arrisRouterAdvAirtimeBSSWeightEntry 2 }

arrisRouterAdvAirtimeSTAWeight OBJECT IDENTIFIER ::= { arrisRouterAirtimeCtrlCfg 102 }

arrisRouterAdvAirtimeSTAWeightDestroyAll OBJECT-TYPE
     SYNTAX         TruthValue
     MAX-ACCESS     read-write
     STATUS         current
     DESCRIPTION    "Destroys all entries in the arrisRouterAdvAirtimeSTAWeightTable"
     DEFVAL {false}
     ::= { arrisRouterAdvAirtimeSTAWeight 1 }

arrisRouterAdvAirtimeSTAWeightTable OBJECT-TYPE
    	SYNTAX		SEQUENCE OF ArrisRouterAdvAirtimeSTAWeightEntry
    	MAX-ACCESS 	not-accessible
    	STATUS		current
    	DESCRIPTION
    		"This table assigns Weights on a per STA Basis."
    	::= { arrisRouterAdvAirtimeSTAWeight 2 }

arrisRouterAdvAirtimeSTAWeightEntry OBJECT-TYPE
	 SYNTAX		ArrisRouterAdvAirtimeSTAWeightEntry
	 MAX-ACCESS not-accessible
	 STATUS		current
	 DESCRIPTION
		"A row in the table of the Advanced Airtime Management STA Weight Table."

     INDEX { arrisRouterAdvAirtimeSTAIndex }
	::= { arrisRouterAdvAirtimeSTAWeightTable 1 }

ArrisRouterAdvAirtimeSTAWeightEntry ::=
     SEQUENCE	{
		  	        arrisRouterAdvAirtimeSTAIndex           Unsigned32,
		  	        arrisRouterAdvAirtimeSTAMAC             MacAddress,
		  	        arrisRouterAdvAirtimeSTAWeightValue     Unsigned32,
		  	        arrisRouterAdvAirtimeSTAPeriod          Unsigned32,
		  	        arrisRouterAdvAirtimeSTAStatus          RowStatus
		  	    }

arrisRouterAdvAirtimeSTAIndex OBJECT-TYPE
    SYNTAX      Unsigned32 (1..50)
    MAX-ACCESS  not-accessible
    STATUS      current
    DESCRIPTION "The Index assigned to the client Entry"
    ::= { arrisRouterAdvAirtimeSTAWeightEntry 1 }

arrisRouterAdvAirtimeSTAMAC OBJECT-TYPE
     SYNTAX		MacAddress
     MAX-ACCESS	read-create
     STATUS		current
     DESCRIPTION "MAC Address of the STA"
     ::= { arrisRouterAdvAirtimeSTAWeightEntry 2 }

arrisRouterAdvAirtimeSTAWeightValue OBJECT-TYPE
     SYNTAX		Unsigned32 (5..100)
     MAX-ACCESS	read-create
     STATUS		current
     DESCRIPTION "Sets the Percentage of Airtime to be allocated to this STA.
                 Also allow 0 which means zero guaranteed airtime."
     ::= { arrisRouterAdvAirtimeSTAWeightEntry 3 }

arrisRouterAdvAirtimeSTAPeriod OBJECT-TYPE
     SYNTAX		Unsigned32
     MAX-ACCESS	read-create
     STATUS		current
     DESCRIPTION "Sets the Period (seconds) of how long the weight must be applied.
                  After this period expires, then weighting for the STA is removed for
                  this specific STA.  If set to zero (0), then the period is infinite
                  until the setting is removed or changed."
     DEFVAL { 0 }
     ::= { arrisRouterAdvAirtimeSTAWeightEntry 4 }

arrisRouterAdvAirtimeSTAStatus OBJECT-TYPE
     SYNTAX      RowStatus
     MAX-ACCESS  read-create
     STATUS      current
     DESCRIPTION
         "The status of this conceptual row.

          To create a row in this table, a manager must set this object to
          either createAndGo(4) or createAndWait(5).

          To destroy a row in this table, a manager must set this object to destroy(6).

          Until instances of all corresponding columns are appropriately
          configured, the value of the corresponding instance of the
          arrisRouterAdvAirtimeSTAStatus column is 'notReady'.

          In particular, a newly created row cannot be made active until the
          corresponding instances of STA_MAC & STA_Weight have been set.

          Only rows with a status of active(1) will be applied."

     ::= { arrisRouterAdvAirtimeSTAWeightEntry 5 }

-- ADD END, Task15083

arrisRouterWiFiGreenModeEnable OBJECT-TYPE
     SYNTAX      TruthValue
     MAX-ACCESS  read-write
     STATUS      current
     DESCRIPTION "Enable or Disable Green mode for WiFi radio(2.4GHz)."
     DEFVAL { false }
     ::= { arrisRouterWirelessCfg 107 }

arrisRouterWiFiGreenModeStatus OBJECT-TYPE
     SYNTAX      INTEGER {
               none(0),
               active(1),
               inactive(2)
               }
     MAX-ACCESS  read-only
     STATUS      current
     DESCRIPTION  "Current status of WiFi Green Mode."
     ::= { arrisRouterWirelessCfg 108 }

arrisRouterWiFiApplySettings OBJECT-TYPE
     SYNTAX      TruthValue
     MAX-ACCESS  read-write
     STATUS      current
     DESCRIPTION "This applies wireless settings."
     ::= { arrisRouterWirelessCfg 1001 }

-- firewall settings

arrisRouterFWEnabled OBJECT-TYPE
    SYNTAX      TruthValue
    MAX-ACCESS  read-write
    STATUS      current
    DESCRIPTION "Is the firewall enabled or not."
    DEFVAL { true }
    ::= { arrisRouterFWCfg 1 }

arrisRouterFWVirtSrvClear OBJECT-TYPE
	SYNTAX		INTEGER { clear(1) }
	MAX-ACCESS	read-write
	STATUS		current
	DESCRIPTION	"Set to clear(1) to clear all virtual server items."
	::= { arrisRouterFWCfg 2 }

arrisRouterFWIPFilterClear OBJECT-TYPE
	SYNTAX		INTEGER { clear(1) }
	MAX-ACCESS	read-write
	STATUS		current
	DESCRIPTION	"Set to clear(1) to clear all IP filtering rules."
	::= { arrisRouterFWCfg 3 }

arrisRouterFWMACFilterClear OBJECT-TYPE
	SYNTAX		INTEGER { clear(1) }
	MAX-ACCESS	read-write
	STATUS		current
	DESCRIPTION	"Set to clear(1) to clear all MAC filter rules."
	::= { arrisRouterFWCfg 4 }

arrisRouterFWPortTrigClear OBJECT-TYPE
	SYNTAX		INTEGER { clear(1) }
	MAX-ACCESS	read-write
	STATUS		current
	DESCRIPTION	"Set to clear(1) to clear all port trigger rules."
	::= { arrisRouterFWCfg 5 }

arrisRouterFWEnableDMZ OBJECT-TYPE
    SYNTAX      TruthValue
    MAX-ACCESS  read-write
    STATUS      current
    DESCRIPTION  "Enable/disable any configured DMZ host."
    ::= { arrisRouterFWCfg 6 }

arrisRouterFWIPAddrTypeDMZ OBJECT-TYPE
    SYNTAX      InetAddressType
    MAX-ACCESS  read-write
    STATUS      current
    DESCRIPTION  "The IP address type of the DMZ host."
    ::= { arrisRouterFWCfg 7 }

arrisRouterFWIPAddrDMZ OBJECT-TYPE
    SYNTAX      InetAddress
    MAX-ACCESS  read-write
    STATUS      current
    DESCRIPTION  "The IP address of the DMZ host."
    ::= { arrisRouterFWCfg 8 }

arrisRouterFWSecurityLevel OBJECT-TYPE
    SYNTAX      INTEGER { unknown(0), minimum(1), medium(2), maximum(3), custom(4) }
    MAX-ACCESS  read-write
    STATUS      current
    DESCRIPTION  "This variable can be used to set a generic firewall 'level'.
                minimum: ALLOWS all incoming and outgoing connections except IDENT (port 113).
                medium: REJECTS all incoming connections and ALLOWS all outgoing connections except IDENT (port 113), ICMP, Kazaa (port 1214), Bittorrent (Ports 6881-6999), Gnutella (6346),
                        Vuze (49152-65534)
                maximum: REJECTS all incoming connections.
                        REJECTS all outgoing connections except for: HTTP (80), HTTPS (443), DNS (53), Email (25,110,143,465,587,993,995), NTP (119, 123), VPN (500, 1723), iTunes (3689)
                custom: Custom port filters and triggers are used."
    ::= { arrisRouterFWCfg 9 }

arrisRouterFWApplySettings OBJECT-TYPE
    SYNTAX      INTEGER { noSet(0), applySettings(1), revertSettings(2), resetDefaults(3) }
    MAX-ACCESS  read-write
    STATUS      current
    DESCRIPTION "Make modifications to any and all items under arrisRouterFWCfg and then apply all of these settings (1) or revert them all back to their
                original settings."
    ::= { arrisRouterFWCfg 10 }


-- Virtual server (port forwarding) table

arrisRouterFWVirtSrvTable  OBJECT-TYPE
    SYNTAX      SEQUENCE OF ArrisRouterFWVirtSrvEntry
    MAX-ACCESS  not-accessible
    STATUS      current
    DESCRIPTION   "A table of 'virtual servers'. This allows for incoming requests on specific port numbers to reach web servers,
                   FTP servers, mail servers, etc. so they can be accessible from the public internet."
    ::= { arrisRouterFWCfg 12 }

arrisRouterFWVirtSrvEntry OBJECT-TYPE
    SYNTAX      ArrisRouterFWVirtSrvEntry
    MAX-ACCESS  not-accessible
    STATUS      current
    DESCRIPTION   "A table of 'virtual servers'. This allows for incoming requests on specific port numbers to reach web servers,
                    FTP servers, mail servers, etc. so they can be accessible from the public internet."
    INDEX   { arrisRouterFWVirtSrvIndex }
    ::= { arrisRouterFWVirtSrvTable 1 }

ArrisRouterFWVirtSrvEntry ::=
    SEQUENCE    {
                arrisRouterFWVirtSrvIndex		Unsigned32,
                arrisRouterFWVirtSrvDesc		DisplayString,
                arrisRouterFWVirtSrvPortStart		Unsigned32,
                arrisRouterFWVirtSrvPortEnd		Unsigned32,
                arrisRouterFWVirtSrvProtoType		INTEGER,
                arrisRouterFWVirtSrvIPAddrType		InetAddressType,
                arrisRouterFWVirtSrvIPAddr		InetAddress,
                arrisRouterFWVirtSrvTOD			Integer32,
                arrisRouterFWVirtSrvLocalPortStart	Unsigned32,
                arrisRouterFWVirtSrvLocalPortEnd	Unsigned32,
                arrisRouterFWVirtSrvRowStatus		RowStatus,
		arrisRouterFWVirtSrvIP2AddrType		InetAddressType,
		arrisRouterFWVirtSrvIP2Addr		InetAddress,
                arrisRouterFWSrvTr69InstanceID          Unsigned32,
                arrisRouterFWVirtSrvEnable              TruthValue
    }

arrisRouterFWVirtSrvIndex OBJECT-TYPE
    SYNTAX      Unsigned32
    MAX-ACCESS  not-accessible
    STATUS      current
    DESCRIPTION
        "Indicates the instance of this table row."
    ::= { arrisRouterFWVirtSrvEntry 1 }

arrisRouterFWVirtSrvDesc OBJECT-TYPE
    SYNTAX      DisplayString (SIZE (0..16))
    MAX-ACCESS  read-create
    STATUS      current
    DESCRIPTION  "A textual description or name for this virtual server, i.e. My FTP."
    ::= { arrisRouterFWVirtSrvEntry 2 }

arrisRouterFWVirtSrvPortStart OBJECT-TYPE
    SYNTAX      Unsigned32 (0..65535)
    MAX-ACCESS  read-create
    STATUS      current
    DESCRIPTION  "The beginning of the port range to forward to this virtual server."
    ::= { arrisRouterFWVirtSrvEntry 3 }

arrisRouterFWVirtSrvPortEnd OBJECT-TYPE
    SYNTAX      Unsigned32 (0..65535)
    MAX-ACCESS  read-create
    STATUS      current
    DESCRIPTION  "The end of the port range to forward to this virtual server."
    ::= { arrisRouterFWVirtSrvEntry 4 }

arrisRouterFWVirtSrvProtoType OBJECT-TYPE
    SYNTAX      INTEGER { udp(0), tcp(1), both(2) }
    MAX-ACCESS  read-create
    STATUS      current
    DESCRIPTION  "Specifies which protocol(s) are forwarded."
    ::= { arrisRouterFWVirtSrvEntry 5 }

arrisRouterFWVirtSrvIPAddrType OBJECT-TYPE
    SYNTAX      InetAddressType
    MAX-ACCESS  read-create
    STATUS      current
    DESCRIPTION  "Type of IP address on private network to forward to."
    ::= { arrisRouterFWVirtSrvEntry 6 }

arrisRouterFWVirtSrvIPAddr OBJECT-TYPE
    SYNTAX      InetAddress
    MAX-ACCESS  read-create
    STATUS      current
    DESCRIPTION  "IP address on private network to forward to."
    ::= { arrisRouterFWVirtSrvEntry 7 }

arrisRouterFWVirtSrvTOD OBJECT-TYPE
    SYNTAX      Integer32
    MAX-ACCESS  read-create
    STATUS      current
    DESCRIPTION  "This is a 32-bit bitmask that sets the time of day to apply and days of the week to apply this rule.
                Bits 0-6 correspond to Sunday-Saturday.  Set the bit high (1) to enable this rule for the day of the week.
                Bits 7-30 apply to hours of the day 00:00:00-23:00:00.  Each bit corresponds to an hour.  Set the bit high to
                enable the rule for specified hour."
    ::= { arrisRouterFWVirtSrvEntry 8 }

arrisRouterFWVirtSrvLocalPortStart OBJECT-TYPE
    SYNTAX      Unsigned32 (0..65535)
    MAX-ACCESS  read-create
    STATUS      current
    DESCRIPTION  "The beginning of the port range to forward to this virtual server."
    ::= { arrisRouterFWVirtSrvEntry 9 }

arrisRouterFWVirtSrvLocalPortEnd OBJECT-TYPE
    SYNTAX      Unsigned32 (0..65535)
    MAX-ACCESS  read-create
    STATUS      current
    DESCRIPTION  "The end of the port range to forward to this virtual server."
    ::= { arrisRouterFWVirtSrvEntry 10 }

arrisRouterFWVirtSrvRowStatus OBJECT-TYPE
    SYNTAX      RowStatus
    MAX-ACCESS  read-create
    STATUS      current
    DESCRIPTION  "Row status to add/remove rows."
    ::= { arrisRouterFWVirtSrvEntry 11 }

arrisRouterFWVirtSrvIP2AddrType OBJECT-TYPE
    SYNTAX      InetAddressType
    MAX-ACCESS  read-create
    STATUS      current
    DESCRIPTION  "Type of second IP address on private network to forward to"
    ::= { arrisRouterFWVirtSrvEntry 12 }

arrisRouterFWVirtSrvIP2Addr OBJECT-TYPE
    SYNTAX      InetAddress
    MAX-ACCESS  read-create
    STATUS      current
    DESCRIPTION  "Second IP address on private network to forward to"
    ::= { arrisRouterFWVirtSrvEntry 13 }

arrisRouterFWSrvTr69InstanceID OBJECT-TYPE
    SYNTAX      Unsigned32 (0..65535)
    MAX-ACCESS  read-create
    STATUS      current
    DESCRIPTION  "The unique ID of Table"
    ::= { arrisRouterFWVirtSrvEntry 14 }

arrisRouterFWVirtSrvEnable OBJECT-TYPE
    SYNTAX      TruthValue
    MAX-ACCESS  read-write
    STATUS      current
    DESCRIPTION "Is the virtual server enabled or not."
    ::= { arrisRouterFWVirtSrvEntry 15 }


-- IP Filtering - filter range(s) of IP addresses to block internet traffic to specific devices on the network

arrisRouterFWIPFilterTable  OBJECT-TYPE
    SYNTAX      SEQUENCE OF ArrisRouterFWIPFilterEntry
    MAX-ACCESS  not-accessible
    STATUS      current
    DESCRIPTION  "A table of IP addresses to filter to block internet traffic to specific devices on the network."
    ::= { arrisRouterFWCfg 13 }

arrisRouterFWIPFilterEntry OBJECT-TYPE
    SYNTAX      ArrisRouterFWIPFilterEntry
    MAX-ACCESS  not-accessible
    STATUS      current
    DESCRIPTION  "A table of IP addresses to filter to block internet traffic to specific devices on the network."
    INDEX   { arrisRouterFWIPFilterIndex }
    ::= { arrisRouterFWIPFilterTable 1 }

ArrisRouterFWIPFilterEntry ::=
    SEQUENCE    {
                arrisRouterFWIPFilterIndex		Unsigned32,
                arrisRouterFWIPFilterDesc		DisplayString,
                arrisRouterFWIPFilterStartType		InetAddressType,
                arrisRouterFWIPFilterStartAddr		InetAddress,
                arrisRouterFWIPFilterEndType		InetAddressType,
                arrisRouterFWIPFilterEndAddr		InetAddress,
                arrisRouterFWIPFilterPortStart		Unsigned32,
                arrisRouterFWIPFilterPortEnd		Unsigned32,
                arrisRouterFWIPFilterProtoType		INTEGER,
                arrisRouterFWIPFilterTOD		Integer32,
                arrisRouterFWIPFilterRowStatus		RowStatus,
                arrisRouterFWIPFilterAction		INTEGER,
                arrisRouterFWIPFilterDirection		INTEGER,
                arrisRouterFWIPFilterStartMin		INTEGER,
                arrisRouterFWIPFilterEndMin		INTEGER,
                arrisRouterFWIPFilterRuleTr69InstanceID			Unsigned32,
                arrisRouterFWIPFilterTimeTr69InstanceID			Unsigned32,
                arrisRouterFWIPFilterTimeTr69LastInstance		Unsigned32
    }

arrisRouterFWIPFilterIndex OBJECT-TYPE
    SYNTAX      Unsigned32
    MAX-ACCESS  not-accessible
    STATUS      current
    DESCRIPTION  "Indicates the instance of this table row."
    ::= { arrisRouterFWIPFilterEntry 1 }

arrisRouterFWIPFilterDesc OBJECT-TYPE
    SYNTAX      DisplayString (SIZE (0..32))
    MAX-ACCESS  read-create
    STATUS      current
    DESCRIPTION  "A textual description or name for this filtering rule/row."
    ::= { arrisRouterFWIPFilterEntry 2 }

arrisRouterFWIPFilterStartType OBJECT-TYPE
    SYNTAX      InetAddressType
    MAX-ACCESS  read-create
    STATUS      current
    DESCRIPTION  "Type of IP address for beginning of range on private network to filter."
    ::= { arrisRouterFWIPFilterEntry 3 }

arrisRouterFWIPFilterStartAddr OBJECT-TYPE
    SYNTAX      InetAddress
    MAX-ACCESS  read-create
    STATUS      current
    DESCRIPTION  "Beginning of IP address range on private network to filter.  To block ports on all IPs use 0.0.0.0 (IPv4)"
    ::= { arrisRouterFWIPFilterEntry 4 }

arrisRouterFWIPFilterEndType OBJECT-TYPE
    SYNTAX      InetAddressType
    MAX-ACCESS  read-create
    STATUS      current
    DESCRIPTION  "Type of IP address for end of range on private network to filter."
    ::= { arrisRouterFWIPFilterEntry 5 }

arrisRouterFWIPFilterEndAddr OBJECT-TYPE
    SYNTAX      InetAddress
    MAX-ACCESS  read-create
    STATUS      current
    DESCRIPTION  "End of IP address range on private network to filter.  To block ports on all IPs use 0.0.0.0 (IPv4)"
    ::= { arrisRouterFWIPFilterEntry 6 }

arrisRouterFWIPFilterPortStart OBJECT-TYPE
    SYNTAX      Unsigned32 (0..65535)
    MAX-ACCESS  read-create
    STATUS      current
    DESCRIPTION  "The beginning of the port range to filter."
    ::= { arrisRouterFWIPFilterEntry 7 }

arrisRouterFWIPFilterPortEnd OBJECT-TYPE
    SYNTAX      Unsigned32 (0..65535)
    MAX-ACCESS  read-create
    STATUS      current
    DESCRIPTION  "The end of the port range to filter."
    ::= { arrisRouterFWIPFilterEntry 8 }

arrisRouterFWIPFilterProtoType OBJECT-TYPE
    SYNTAX      INTEGER { udp(0), tcp(1), both(2) }
    MAX-ACCESS  read-create
    STATUS      current
    DESCRIPTION  "Specifies which protocol(s) are filtered."
    ::= { arrisRouterFWIPFilterEntry 9 }

arrisRouterFWIPFilterTOD OBJECT-TYPE
    SYNTAX      Integer32
    MAX-ACCESS  read-create
    STATUS      current
    DESCRIPTION  "This is a 32-bit bitmask that sets the time of day to apply and days of the week to apply this rule.
                Bits 0-6 correspond to Sunday-Saturday.  Set the bit high (1) to enable this rule for the day of the week.
                Bits 7-30 apply to hours of the day 00:00:00-23:00:00.  Each it corresponds to an hour.  Set the bit high to
                enable the rule for specified hour."
    ::= { arrisRouterFWIPFilterEntry 10 }

arrisRouterFWIPFilterRowStatus OBJECT-TYPE
    SYNTAX      RowStatus
    MAX-ACCESS  read-create
    STATUS      current
    DESCRIPTION  "Row status to add/remove rows."
    ::= { arrisRouterFWIPFilterEntry 11 }

arrisRouterFWIPFilterAction OBJECT-TYPE
    SYNTAX      INTEGER { allow(0), deny(1) }
    MAX-ACCESS  read-create
    STATUS      current
    DESCRIPTION  "Does rule allow or deny access."
    ::= { arrisRouterFWIPFilterEntry 12 }

arrisRouterFWIPFilterDirection OBJECT-TYPE
    SYNTAX      INTEGER { incoming(0), outgoing(1) }
    MAX-ACCESS  read-create
    STATUS      current
    DESCRIPTION  "Does rule apply to incoming or outgoing packets."
    ::= { arrisRouterFWIPFilterEntry 13 }

arrisRouterFWIPFilterStartMin OBJECT-TYPE
    SYNTAX     INTEGER
    MAX-ACCESS  read-create
    STATUS      current
    DESCRIPTION  "start minute means minutes counting from 00:00 each day (range:0~1439), eg. 02:30 expressed 150 mins"
    ::= { arrisRouterFWIPFilterEntry 14 }

arrisRouterFWIPFilterEndMin OBJECT-TYPE
    SYNTAX     INTEGER
    MAX-ACCESS  read-create
    STATUS      current
    DESCRIPTION  "end minute means minutes counting from 00:00 each day (range:0~1439), eg. 02:30 expressed 150 mins"
    ::= { arrisRouterFWIPFilterEntry 15 }

arrisRouterFWIPFilterRuleTr69InstanceID OBJECT-TYPE
    SYNTAX      Unsigned32
    MAX-ACCESS  read-create
    STATUS      current
    DESCRIPTION  "The rule instance mapping for Device.X_ARRIS_COM_Firewall.IPFilter.Rule.{i}."
    ::= { arrisRouterFWIPFilterEntry 16 }

arrisRouterFWIPFilterTimeTr69InstanceID OBJECT-TYPE
    SYNTAX      Unsigned32
    MAX-ACCESS  read-create
    STATUS      current
    DESCRIPTION  "The time instance mapping for Device.X_ARRIS_COM_Firewall.IPFilter.Rule.{i}.Day.{i}.Time.{i}."
    ::= { arrisRouterFWIPFilterEntry 17 }

arrisRouterFWIPFilterTimeTr69LastInstance OBJECT-TYPE
    SYNTAX      Unsigned32
    MAX-ACCESS  read-write
    STATUS      current
    DESCRIPTION "A count indicates that how many instance TR-069 is created under Device.X_ARRIS_COM_Firewall.IPFilter.Rule.{i}.Day.{i}.Time.{i}."
    ::= { arrisRouterFWIPFilterEntry 18 }

-- Firewall filtering based on MAC-address

arrisRouterFWAllowAll OBJECT-TYPE
    SYNTAX      TruthValue
    MAX-ACCESS  read-write
    STATUS      current
    DESCRIPTION  "Set to true to allow all devices to connect to the network EXCEPT those in the arrisRouterFWMACFilterTable.
                    Set to false to block all devices from connecting to the network EXCEPT those in the arrisRouterFWMACFilterTable."
    ::= { arrisRouterFWCfg 14 }

arrisRouterFWMACFilterTable  OBJECT-TYPE
    SYNTAX      SEQUENCE OF ArrisRouterFWMACFilterEntry
    MAX-ACCESS  not-accessible
    STATUS      current
    DESCRIPTION  "A table of MAC addresses which are filtered/blocked by the firewall."
    ::= { arrisRouterFWCfg 15 }

arrisRouterFWMACFilterEntry OBJECT-TYPE
    SYNTAX      ArrisRouterFWMACFilterEntry
    MAX-ACCESS  not-accessible
    STATUS      current
    DESCRIPTION  "A table of MAC addresses which are blocked or allowed by the firewall.  The behavior depends on arrisRouterFWAllowAll.
                  The ifIndex usually to be the Lan interface ifIndex, like 200."
    INDEX   { ifIndex, arrisRouterFWMACFilterIndex }
    ::= { arrisRouterFWMACFilterTable 1 }

ArrisRouterFWMACFilterEntry ::=
    SEQUENCE    {
                arrisRouterFWMACFilterIndex		Unsigned32,
                arrisRouterFWMACFilterAddr		MacAddress,
                arrisRouterFWMACFilterTOD		Integer32,
                arrisRouterFWMACFilterRowStatus		RowStatus,
                arrisRouterFWMACFilterHostName		DisplayString,
                arrisRouterFWMACFilterStartMin		INTEGER,
                arrisRouterFWMACFilterEndMin		INTEGER,
                arrisRouterFWMACFilterRuleTr69InstanceID        Unsigned32,
                arrisRouterFWMACFilterTimeTr69InstanceID        Unsigned32,
                arrisRouterFWMACFilterTimeTr69LastInstance      Unsigned32
    }

arrisRouterFWMACFilterIndex OBJECT-TYPE
    SYNTAX      Unsigned32
    MAX-ACCESS  not-accessible
    STATUS      current
    DESCRIPTION  "Indicates the instance of this table row."
    ::= { arrisRouterFWMACFilterEntry 1 }

arrisRouterFWMACFilterAddr OBJECT-TYPE
    SYNTAX      MacAddress
    MAX-ACCESS  read-create
    STATUS      current
    DESCRIPTION "A MAC address of a device on the local network which is filtered/blocked by the firewall."
    ::= { arrisRouterFWMACFilterEntry 2 }

arrisRouterFWMACFilterTOD OBJECT-TYPE
    SYNTAX      Integer32
    MAX-ACCESS  read-create
    STATUS      current
    DESCRIPTION  "This is a 32-bit bitmask that sets the time of day to apply and days of the week to apply this rule.
                Bits 0-6 correspond to Sunday-Saturday.  Set the bit high (1) to enable this rule for the day of the week.
                Bits 7-30 apply to hours of the day 00:00:00-23:00:00.  Each it corresponds to an hour.  Set the bit high to
                enable the rule for specified hour."
    ::= { arrisRouterFWMACFilterEntry 3 }

arrisRouterFWMACFilterRowStatus OBJECT-TYPE
    SYNTAX      RowStatus
    MAX-ACCESS  read-create
    STATUS      current
    DESCRIPTION  "Row status to add/remove rows."
    ::= { arrisRouterFWMACFilterEntry 4 }

arrisRouterFWMACFilterHostName OBJECT-TYPE
    SYNTAX      DisplayString
    MAX-ACCESS  read-create
    STATUS      current
    DESCRIPTION  "The name of the device on the local network which is filtered/blocked by the firewall."
    ::= { arrisRouterFWMACFilterEntry 5 }

arrisRouterFWMACFilterStartMin OBJECT-TYPE
    SYNTAX     INTEGER
    MAX-ACCESS  read-create
    STATUS      current
    DESCRIPTION  "start minute means minutes counting from 00:00 each day (range:0~1439), eg. 02:30 expressed 150 mins"
    ::= { arrisRouterFWMACFilterEntry 6 }

arrisRouterFWMACFilterEndMin OBJECT-TYPE
    SYNTAX     INTEGER
    MAX-ACCESS  read-create
    STATUS      current
    DESCRIPTION  "end minute means minutes counting from 00:00 each day (range:0~1439), eg. 02:30 expressed 150 mins"
    ::= { arrisRouterFWMACFilterEntry 7 }

arrisRouterFWMACFilterRuleTr69InstanceID OBJECT-TYPE
    SYNTAX      Unsigned32
    MAX-ACCESS  read-create
    STATUS      current
    DESCRIPTION  "The rule instance mapping for Device.X_ARRIS_COM_Firewall.MACFilter.Rule.{i}."
    ::= { arrisRouterFWMACFilterEntry 8 }

arrisRouterFWMACFilterTimeTr69InstanceID OBJECT-TYPE
    SYNTAX      Unsigned32
    MAX-ACCESS  read-create
    STATUS      current
    DESCRIPTION  "The time instance mapping for Device.X_ARRIS_COM_Firewall.MACFilter.Rule.{i}.Day.{i}.Time.{i}."
    ::= { arrisRouterFWMACFilterEntry 9 }

arrisRouterFWMACFilterTimeTr69LastInstance OBJECT-TYPE
    SYNTAX      Unsigned32
    MAX-ACCESS  read-write
    STATUS      current
    DESCRIPTION "A count indicates that how many instance TR-069 is created under Device.X_ARRIS_COM_Firewall.MACFilter.Rule.{i}.Day.{i}.Time.{i}."
    ::= { arrisRouterFWMACFilterEntry 10 }

-- Port Triggering

arrisRouterFWPortTrigTable  OBJECT-TYPE
    SYNTAX      SEQUENCE OF ArrisRouterFWPortTrigEntry
    MAX-ACCESS  not-accessible
    STATUS      current
    DESCRIPTION  "A table of port Trigs.  This allows configuration of dynamic triggers to specific devices on the Lan
                  This allows for special applications that require specific port numbers with bi-directional traffic to function properly.
                  Applications such as video conferencing, voice, gaming, and some messenging program features may require these special settings."
    ::= { arrisRouterFWCfg 16 }

arrisRouterFWPortTrigEntry OBJECT-TYPE
    SYNTAX      ArrisRouterFWPortTrigEntry
    MAX-ACCESS  not-accessible
    STATUS      current
    DESCRIPTION  "A table of port Trigs.  This allows configuration of dynamic triggers to specific devices on the Lan
                  This allows for special applications that require specific port numbers with bi-directional traffic to function properly.
                  Applications such as video conferencing, voice, gaming, and some messenging program features may require these special settings."
    INDEX   { arrisRouterFWPortTrigIndex }
    ::= { arrisRouterFWPortTrigTable 1 }

ArrisRouterFWPortTrigEntry ::=
    SEQUENCE    {
                arrisRouterFWPortTrigIndex		Unsigned32,
                arrisRouterFWPortTrigDesc		DisplayString,
                arrisRouterFWPortTrigPortStart		Unsigned32,
                arrisRouterFWPortTrigPortEnd		Unsigned32,
                arrisRouterFWPortTargPortStart		Unsigned32,
                arrisRouterFWPortTargPortEnd		Unsigned32,
                arrisRouterFWPortTrigProtoType		INTEGER,
                arrisRouterFWPortTrigTOD		Integer32,
                arrisRouterFWPortTrigRowStatus		RowStatus
            }

arrisRouterFWPortTrigIndex OBJECT-TYPE
    SYNTAX      Unsigned32
    MAX-ACCESS  not-accessible
    STATUS      current
    DESCRIPTION  "Indicates the instance of this table row."
    ::= { arrisRouterFWPortTrigEntry 1 }

arrisRouterFWPortTrigDesc OBJECT-TYPE
    SYNTAX      DisplayString (SIZE (0..16))
    MAX-ACCESS  read-create
    STATUS      current
    DESCRIPTION  "A textual description or name for this port trigger."
    ::= { arrisRouterFWPortTrigEntry 2 }

arrisRouterFWPortTrigPortStart OBJECT-TYPE
    SYNTAX      Unsigned32 (0..65535)
    MAX-ACCESS  read-create
    STATUS      current
    DESCRIPTION  "The beginning of the trigger port range."
    ::= { arrisRouterFWPortTrigEntry 3 }

arrisRouterFWPortTrigPortEnd OBJECT-TYPE
    SYNTAX      Unsigned32 (0..65535)
    MAX-ACCESS  read-create
    STATUS      current
    DESCRIPTION  "The end of the trigger port range."
    ::= { arrisRouterFWPortTrigEntry 4 }

arrisRouterFWPortTargPortStart OBJECT-TYPE
    SYNTAX      Unsigned32 (0..65535)
    MAX-ACCESS  read-create
    STATUS      current
    DESCRIPTION  "The beginning of the target port range."
    ::= { arrisRouterFWPortTrigEntry 5 }

arrisRouterFWPortTargPortEnd OBJECT-TYPE
    SYNTAX      Unsigned32 (0..65535)
    MAX-ACCESS  read-create
    STATUS      current
    DESCRIPTION  "The end of the target port range."
    ::= { arrisRouterFWPortTrigEntry 6 }

arrisRouterFWPortTrigProtoType OBJECT-TYPE
    SYNTAX      INTEGER { udp(0), tcp(1), both(2) }
    MAX-ACCESS  read-create
    STATUS      current
    DESCRIPTION  "Specifies which protocol(s) are filtered."
    ::= { arrisRouterFWPortTrigEntry 7 }

arrisRouterFWPortTrigTOD OBJECT-TYPE
    SYNTAX      Integer32
    MAX-ACCESS  read-write
    STATUS      current
    DESCRIPTION  "This is a 32-bit bitmask that sets the time of day to apply and days of the week to apply this rule.
                Bits 0-6 correspond to Sunday-Saturday.  Set the bit high (1) to enable this rule for the day of the week.
                Bits 7-30 apply to hours of the day 00:00:00-23:00:00.  Each it corresponds to an hour.  Set the bit high to
                enable the rule for specified hour."
    ::= { arrisRouterFWPortTrigEntry 8 }

arrisRouterFWPortTrigRowStatus OBJECT-TYPE
    SYNTAX      RowStatus
    MAX-ACCESS  read-create
    STATUS      current
    DESCRIPTION  "Row status to add/remove rows."
    ::= { arrisRouterFWPortTrigEntry 9 }


arrisRouterFWFilterRules			 OBJECT IDENTIFIER ::= { arrisRouterFWCfg 17 }

arrisRouterFWFilterProxy OBJECT-TYPE
    SYNTAX      TruthValue
    MAX-ACCESS  read-write
    STATUS      current
    DESCRIPTION  "Enable/disable filtering of HTTP proxy."
    DEFVAL	{ false }
    ::= { arrisRouterFWFilterRules 1 }

arrisRouterFWFilterCookies OBJECT-TYPE
    SYNTAX      TruthValue
    MAX-ACCESS  read-write
    STATUS      current
    DESCRIPTION  "Enable/disable filtering of cookies."
    DEFVAL	{ false }
    ::= { arrisRouterFWFilterRules 2 }

arrisRouterFWFilterJavaApplets OBJECT-TYPE
    SYNTAX      TruthValue
    MAX-ACCESS  read-write
    STATUS      current
    DESCRIPTION  "Enable/disable filtering of Java applets."
    DEFVAL	{ false }
    ::= { arrisRouterFWFilterRules 3 }

arrisRouterFWFilterActiveX OBJECT-TYPE
    SYNTAX      TruthValue
    MAX-ACCESS  read-write
    STATUS      current
    DESCRIPTION  "Enable/disable filtering of ActiveX controls."
    DEFVAL	{ false }
    ::= { arrisRouterFWFilterRules 4 }

arrisRouterFWFilterPopupWnds OBJECT-TYPE
    SYNTAX      TruthValue
    MAX-ACCESS  read-write
    STATUS      current
    DESCRIPTION  "Enable/disable filtering of popup windows."
    DEFVAL	{ false }
    ::= { arrisRouterFWFilterRules 5 }

arrisRouterFWBlockFragIPPkts OBJECT-TYPE
    SYNTAX      TruthValue
    MAX-ACCESS  read-write
    STATUS      current
    DESCRIPTION  "Enable/disable blocking of fragmented IP packets."
    DEFVAL	{ false }
    ::= { arrisRouterFWFilterRules 6 }

arrisRouterFWPortScanProtect OBJECT-TYPE
    SYNTAX      TruthValue
    MAX-ACCESS  read-write
    STATUS      current
    DESCRIPTION  "Enable/disable port scan protection."
    DEFVAL	{ false }
    ::= { arrisRouterFWFilterRules 7 }

arrisRouterFWIPFloodDetect OBJECT-TYPE
    SYNTAX      TruthValue
    MAX-ACCESS  read-write
    STATUS      current
    DESCRIPTION  "Enable/disable detection of IP floods."
    DEFVAL	{ true }
    ::= { arrisRouterFWFilterRules 8 }

arrisRouterFWBlockFragIPPktsV4 OBJECT-TYPE
    SYNTAX      TruthValue
    MAX-ACCESS  read-write
    STATUS      current
    DESCRIPTION  "Enable/disable blocking of fragmented IPv4 packets. Six MIBs arrisRouterFWBlockFragIPPktsV4, arrisRouterFWPortScanProtectV4, arrisRouterFWIPFloodDetectV4, arrisRouterFWBlockFragIPPktsV6, arrisRouterFWPortScanProtectV6, arrisRouterFWIPFloodDetectV6 are used to seperate Port scan, fragment block and Dos attack enable/disable into IPv4 and IPv6 respectively. They are only used for LGI at present. The original mibs arrisRouterFWBlockFragIPPkts, arrisRouterFWPortScanProtect and arrisRouterFWIPFloodDetect are still used for implemention for IPv4 and IPv6 together, and are used for Non-LGI customers at present."
    DEFVAL  { false }
    ::= { arrisRouterFWFilterRules 9 }

arrisRouterFWPortScanProtectV4 OBJECT-TYPE
    SYNTAX      TruthValue
    MAX-ACCESS  read-write
    STATUS      current
    DESCRIPTION  "Enable/disable IPv4 port scan protection. Six MIBs arrisRouterFWBlockFragIPPktsV4, arrisRouterFWPortScanProtectV4, arrisRouterFWIPFloodDetectV4, arrisRouterFWBlockFragIPPktsV6, arrisRouterFWPortScanProtectV6, arrisRouterFWIPFloodDetectV6 are used to seperate Port scan, fragment block and Dos attack enable/disable into IPv4 and IPv6 respectively. They are only used for LGI at present. The original mibs arrisRouterFWBlockFragIPPkts, arrisRouterFWPortScanProtect and arrisRouterFWIPFloodDetect are still used for implemention for IPv4 and IPv6 together, and are used for Non-LGI customers at present."
    DEFVAL	{ false }
    ::= { arrisRouterFWFilterRules 10 }

arrisRouterFWIPFloodDetectV4 OBJECT-TYPE
    SYNTAX      TruthValue
    MAX-ACCESS  read-write
    STATUS      current
    DESCRIPTION  "Enable/disable detection of IPv4 floods. Six MIBs arrisRouterFWBlockFragIPPktsV4, arrisRouterFWPortScanProtectV4, arrisRouterFWIPFloodDetectV4, arrisRouterFWBlockFragIPPktsV6, arrisRouterFWPortScanProtectV6, arrisRouterFWIPFloodDetectV6 are used to seperate Port scan, fragment block and Dos attack enable/disable into IPv4 and IPv6 respectively. They are only used for LGI at present. The original mibs arrisRouterFWBlockFragIPPkts, arrisRouterFWPortScanProtect and arrisRouterFWIPFloodDetect are still used for implemention for IPv4 and IPv6 together, and are used for Non-LGI customers at present."
    DEFVAL	{ true }
    ::= { arrisRouterFWFilterRules 11 }

arrisRouterFWBlockFragIPPktsV6 OBJECT-TYPE
    SYNTAX      TruthValue
    MAX-ACCESS  read-write
    STATUS      current
    DESCRIPTION  "Enable/disable blocking of fragmented IPv6 packets. Six MIBs arrisRouterFWBlockFragIPPktsV4, arrisRouterFWPortScanProtectV4, arrisRouterFWIPFloodDetectV4, arrisRouterFWBlockFragIPPktsV6, arrisRouterFWPortScanProtectV6, arrisRouterFWIPFloodDetectV6 are used to seperate Port scan, fragment block and Dos attack enable/disable into IPv4 and IPv6 respectively. They are only used for LGI at present. The original mibs arrisRouterFWBlockFragIPPkts, arrisRouterFWPortScanProtect and arrisRouterFWIPFloodDetect are still used for implemention for IPv4 and IPv6 together, and are used for Non-LGI customers at present."
    DEFVAL  { false }
    ::= { arrisRouterFWFilterRules 12 }

arrisRouterFWPortScanProtectV6 OBJECT-TYPE
    SYNTAX      TruthValue
    MAX-ACCESS  read-write
    STATUS      current
    DESCRIPTION  "Enable/disable IPv6 port scan protection. Six MIBs arrisRouterFWBlockFragIPPktsV4, arrisRouterFWPortScanProtectV4, arrisRouterFWIPFloodDetectV4, arrisRouterFWBlockFragIPPktsV6, arrisRouterFWPortScanProtectV6, arrisRouterFWIPFloodDetectV6 are used to seperate Port scan, fragment block and Dos attack enable/disable into IPv4 and IPv6 respectively. They are only used for LGI at present. The original mibs arrisRouterFWBlockFragIPPkts, arrisRouterFWPortScanProtect and arrisRouterFWIPFloodDetect are still used for implemention for IPv4 and IPv6 together, and are used for Non-LGI customers at present."
    DEFVAL	{ false }
    ::= { arrisRouterFWFilterRules 13 }

arrisRouterFWIPFloodDetectV6 OBJECT-TYPE
    SYNTAX      TruthValue
    MAX-ACCESS  read-write
    STATUS      current
    DESCRIPTION  "Enable/disable detection of IPv6 floods. Six MIBs arrisRouterFWBlockFragIPPktsV4, arrisRouterFWPortScanProtectV4, arrisRouterFWIPFloodDetectV4, arrisRouterFWBlockFragIPPktsV6, arrisRouterFWPortScanProtectV6, arrisRouterFWIPFloodDetectV6 are used to seperate Port scan, fragment block and Dos attack enable/disable into IPv4 and IPv6 respectively. They are only used for LGI at present. The original mibs arrisRouterFWBlockFragIPPkts, arrisRouterFWPortScanProtect and arrisRouterFWIPFloodDetect are still used for implemention for IPv4 and IPv6 together, and are used for Non-LGI customers at present."
    DEFVAL	{ true }
    ::= { arrisRouterFWFilterRules 14 }

arrisRouterFWDDNSObjs			 OBJECT IDENTIFIER ::= { arrisRouterFWCfg 18 }

arrisRouterFWDDNSEnable OBJECT-TYPE
    SYNTAX      TruthValue
    MAX-ACCESS  read-write
    STATUS      current
    DESCRIPTION  "Enable/disable dynamic DNS."
    DEFVAL	{ false }
    ::= { arrisRouterFWDDNSObjs 1 }

arrisRouterFWDDNSType OBJECT-TYPE
    SYNTAX      INTEGER { unknown(0), dynDNS(1), tzo(2), freeDNS(3), zoneEdit(4), noIP(5), easyDNS(6), domainsGoogle(7) }
    MAX-ACCESS  read-write
    STATUS      current
    DESCRIPTION  "Type of Dynamic DNS."
    ::= { arrisRouterFWDDNSObjs 2 }

arrisRouterFWDDNSUserName OBJECT-TYPE
    SYNTAX      DisplayString (SIZE (0..64))
    MAX-ACCESS  read-write
    STATUS      current
    DESCRIPTION  "User name to login to dynamic DNS service."
    ::= { arrisRouterFWDDNSObjs 3 }

arrisRouterFWDDNSPassword OBJECT-TYPE
    SYNTAX      DisplayString (SIZE (0..64))
    MAX-ACCESS  read-write
    STATUS      current
    DESCRIPTION  "Password to login to dynamic DNS service."
    ::= { arrisRouterFWDDNSObjs 4 }

arrisRouterFWDDNSDomainName OBJECT-TYPE
    SYNTAX      DisplayString (SIZE (0..255))
    MAX-ACCESS  read-write
    STATUS      current
    DESCRIPTION  "Domain nanme for dynamic DNS service."
    ::= { arrisRouterFWDDNSObjs 5 }

arrisRouterFWDDNSIPAddrType OBJECT-TYPE
    SYNTAX      InetAddressType
    MAX-ACCESS  read-only
    STATUS      current
    DESCRIPTION  "Type for current DDNS IP address."
    ::= { arrisRouterFWDDNSObjs 6 }

arrisRouterFWDDNSIPAddr OBJECT-TYPE
    SYNTAX      InetAddress
    MAX-ACCESS  read-only
    STATUS      current
    DESCRIPTION  "Current DDNS IP address."
    ::= { arrisRouterFWDDNSObjs 7 }

arrisRouterFWDDNSStatus OBJECT-TYPE
    SYNTAX      DisplayString (SIZE (0..255))
    MAX-ACCESS  read-only
    STATUS      current
    DESCRIPTION  "String representing current status of DDNS service."
    ::= { arrisRouterFWDDNSObjs 8 }

arrisRouterFWDDNSHttpsSupport OBJECT-TYPE
    SYNTAX      TruthValue
    MAX-ACCESS  read-write
    STATUS      current
    DESCRIPTION  "Enable/disable HTTPS support"
    ::= { arrisRouterFWDDNSObjs 9 }

arrisRouterFWFeatures		OBJECT IDENTIFIER ::= { arrisRouterFWCfg 19 }

arrisRouterFWEnableWanBlocking OBJECT-TYPE
    SYNTAX      TruthValue
    MAX-ACCESS  read-write
    STATUS      current
    DESCRIPTION  "Enable/disable Wan blocking."
    DEFVAL { false }
    ::= { arrisRouterFWFeatures 1 }

arrisRouterFWIPSecPassThru OBJECT-TYPE
    SYNTAX      TruthValue
    MAX-ACCESS  read-write
    STATUS      current
    DESCRIPTION  "Enable/disable IPSEC passthru."
    DEFVAL { false }
    ::= { arrisRouterFWFeatures 2 }

arrisRouterFWPPTPPassThru OBJECT-TYPE
    SYNTAX      TruthValue
    MAX-ACCESS  read-write
    STATUS      current
    DESCRIPTION  "Enable/disable PPTP passthru."
    DEFVAL { false }
    ::= { arrisRouterFWFeatures 3 }

arrisRouterFWEnableMulticast OBJECT-TYPE
    SYNTAX      TruthValue
    MAX-ACCESS  read-write
    STATUS      current
    DESCRIPTION  "Enable/disable multicast support.
                  NOTE: The default value for this mib is true when Time Warner uses TS9.x loads."
    DEFVAL { false }
    ::= { arrisRouterFWFeatures 4 }

arrisRouterFWEnableRemoteMgmt OBJECT-TYPE
    SYNTAX      TruthValue
    MAX-ACCESS  read-write
    STATUS      current
    DESCRIPTION  "Enable/disable remote web management."
    DEFVAL { false }
    ::= { arrisRouterFWFeatures 5 }

arrisRouterFWEnableRGPassThru OBJECT-TYPE
    SYNTAX      TruthValue
    MAX-ACCESS  read-write
    STATUS      current
    DESCRIPTION  "Enable/disable pass thru mode. If this is enabled UPnP will be automatically disabled. The router must be rebooted after enabling this feature."
    DEFVAL { false }
    ::= { arrisRouterFWFeatures 6 }

arrisRouterFWL2TPPassThru OBJECT-TYPE
    SYNTAX      TruthValue
    MAX-ACCESS  read-write
    STATUS      current
    DESCRIPTION  "Enable/disable L2TP passthru."
    DEFVAL { false }
    ::= { arrisRouterFWFeatures 7 }

arrisRouterFWEnableWanSNMP OBJECT-TYPE
    SYNTAX      TruthValue
    MAX-ACCESS  read-write
    STATUS      current
    DESCRIPTION  "Enable/disable SNMP access (ports 161, 1161, 162) on the eRouter WAN port.
                    Setting/changing this variable's value takes affect without 'applying' settings."
    DEFVAL { false }
    ::= { arrisRouterFWFeatures 8 }

arrisRouterFWEnableWanSSH OBJECT-TYPE
    SYNTAX      TruthValue
    MAX-ACCESS  read-write
    STATUS      current
    DESCRIPTION  "Enable/disable SSH access (port 22) on the eRouter WAN port.
                Setting/changing this variable's value takes affect without 'applying' settings."
    DEFVAL { false }
    ::= { arrisRouterFWFeatures 9 }

arrisRouterFWEnableLanSNMPWireless OBJECT-TYPE
    SYNTAX      TruthValue
    MAX-ACCESS  read-write
    STATUS      current
    DESCRIPTION  "Enable/disable SNMP access (port 1161/161) on the eRouter LAN port for Wireless devices.
                Setting/changing this variable's value takes affect without 'applying' settings.
                This value should ONLY be set from the CMTS/WAN side for in-home troubleshooting by a technician.
                This value will NOT persist.
                This value only applies to the Media Gateway products at this time."
    DEFVAL { false }
    ::= { arrisRouterFWFeatures 10 }

arrisRouterFWAllowDirectedBroadcastPackets OBJECT-TYPE
    SYNTAX      TruthValue
    MAX-ACCESS  read-write
    STATUS      current
    DESCRIPTION  "By default the firewall blocks all traffic to 0.0.0.255. There may be some network addresses that are unreachable due to this.
					Set this value to true to allow traffice to 0.0.0.255 to pass thru the firewall"
    DEFVAL { false }
    ::= { arrisRouterFWFeatures 11 }

arrisRouterFWRemoteMgmt 	OBJECT IDENTIFIER ::= { arrisRouterFWFeatures 12 }

arrisRouterFWRemoteMgmtHttp OBJECT-TYPE
    SYNTAX      TruthValue
    MAX-ACCESS  read-write
    STATUS      current
    DESCRIPTION  "Enable/disable WAN HTTP."
    DEFVAL { false }
    ::= { arrisRouterFWRemoteMgmt 1 }

arrisRouterFWRemoteMgmtHttps OBJECT-TYPE
    SYNTAX      TruthValue
    MAX-ACCESS  read-write
    STATUS      current
    DESCRIPTION  "Enable/disable WAN HTTPs."
    DEFVAL { false }
    ::= { arrisRouterFWRemoteMgmt 2 }

arrisRouterFWRemoteMgmtHttpPort OBJECT-TYPE
    SYNTAX      Integer32 (1..65535)
    MAX-ACCESS  read-write
    STATUS      current
    DESCRIPTION  "WAN HTTP port."
    DEFVAL { 8080 }
    ::= { arrisRouterFWRemoteMgmt 3 }

arrisRouterFWRemoteMgmtHttpsPort OBJECT-TYPE
    SYNTAX      Integer32 (1..65535)
    MAX-ACCESS  read-write
    STATUS      current
    DESCRIPTION  "WAN HTTPs port."
    DEFVAL { 8181 }
    ::= { arrisRouterFWRemoteMgmt 4 }

arrisRouterFWRemoteMgmtAllowedType OBJECT-TYPE
    SYNTAX      INTEGER { singleComputer(1), rangeOfIP(2), anyComputer(3) }
    MAX-ACCESS  read-write
    STATUS      current
    DESCRIPTION  "WAN Allowed type."
    DEFVAL { 3 }
    ::= { arrisRouterFWRemoteMgmt 5 }

arrisRouterFWRemoteMgmtAllowedIPv4 OBJECT-TYPE
    SYNTAX      InetAddress
    MAX-ACCESS  read-write
    STATUS      current
    DESCRIPTION "IPv4 address for WAN Allowed singleComputer."
    ::= { arrisRouterFWRemoteMgmt 6 }

arrisRouterFWRemoteMgmtAllowedIPv6 OBJECT-TYPE
    SYNTAX      InetAddress
    MAX-ACCESS  read-write
    STATUS      current
    DESCRIPTION "IPv6 address for WAN Allowed singleComputer."
    ::= { arrisRouterFWRemoteMgmt 7 }

arrisRouterFWRemoteMgmtAllowedStartIPv4 OBJECT-TYPE
    SYNTAX      InetAddress
    MAX-ACCESS  read-write
    STATUS      current
    DESCRIPTION "IPv4 start address for WAN Allowed rangeOfIP."
    ::= { arrisRouterFWRemoteMgmt 8 }

arrisRouterFWRemoteMgmtAllowedEndIPv4 OBJECT-TYPE
    SYNTAX      InetAddress
    MAX-ACCESS  read-write
    STATUS      current
    DESCRIPTION "IPv4 end address for WAN Allowed rangeOfIP."
    ::= { arrisRouterFWRemoteMgmt 9 }

arrisRouterFWRemoteMgmtAllowedStartIPv6 OBJECT-TYPE
    SYNTAX      InetAddress
    MAX-ACCESS  read-write
    STATUS      current
    DESCRIPTION "IPv6 start address for WAN Allowed rangeOfIP."
    ::= { arrisRouterFWRemoteMgmt 10 }

arrisRouterFWRemoteMgmtAllowedEndIPv6 OBJECT-TYPE
    SYNTAX      InetAddress
    MAX-ACCESS  read-write
    STATUS      current
    DESCRIPTION "IPv6 end address for WAN Allowed rangeOfIP."
    ::= { arrisRouterFWRemoteMgmt 11 }

arrisRouterFWRemoteMgmtTelnet OBJECT-TYPE
    SYNTAX      TruthValue
    MAX-ACCESS  read-write
    STATUS      current
    DESCRIPTION  "Enable/disable WAN Telnet."
    DEFVAL { false }
    ::= { arrisRouterFWRemoteMgmt 12 }

arrisRouterFWSelectRemoteMgmt OBJECT-TYPE
    SYNTAX      TruthValue
    MAX-ACCESS  read-write
    STATUS      current
    DESCRIPTION  "Fireware select Remote Management vs WAN ACL to control GW IP."
    ::= { arrisRouterFWFeatures 13 }

arrisRouterFWParentalControls OBJECT IDENTIFIER ::= { arrisRouterFWCfg 20 }

arrisRouterKeywordCount  OBJECT-TYPE
    SYNTAX      Integer32
    MAX-ACCESS  read-only
    STATUS      current
    DESCRIPTION "Current count of keywords in blocktable."
    ::= { arrisRouterFWParentalControls 1 }

arrisRouterKeywordClear OBJECT-TYPE
    SYNTAX      INTEGER { clear(1) }
    MAX-ACCESS  read-write
    STATUS      current
    DESCRIPTION "Set to clear(1) to clear the entire list/table of keywords in blocktable."
    ::= { arrisRouterFWParentalControls 2 }

arrisRouterBlackListCount  OBJECT-TYPE
    SYNTAX      Integer32
    MAX-ACCESS  read-only
    STATUS      current
    DESCRIPTION "Current count of black listed domains."
    ::= { arrisRouterFWParentalControls 3 }

arrisRouterBlackListClear OBJECT-TYPE
    SYNTAX      INTEGER { clear(1) }
    MAX-ACCESS  read-write
    STATUS      current
    DESCRIPTION "Set to clear(1) to clear the entire list/table of black listed domains."
    ::= { arrisRouterFWParentalControls 4 }

arrisRouterWhiteListCount  OBJECT-TYPE
    SYNTAX      Integer32
    MAX-ACCESS  read-only
    STATUS      current
    DESCRIPTION "Current count of White listed domains."
    ::= { arrisRouterFWParentalControls 5 }

arrisRouterWhiteListClear OBJECT-TYPE
    SYNTAX      INTEGER { clear(1) }
    MAX-ACCESS  read-write
    STATUS      current
    DESCRIPTION "Set to clear(1) to clear the entire list/table of White listed domains."
    ::= { arrisRouterFWParentalControls 6 }

arrisRouterTrustedDeviceCount  OBJECT-TYPE
    SYNTAX      Integer32
    MAX-ACCESS  read-only
    STATUS      current
    DESCRIPTION "Current count of trusted devices which bypass parental controls."
    ::= { arrisRouterFWParentalControls 7 }

arrisRouterTrustedDeviceClear OBJECT-TYPE
    SYNTAX      INTEGER { clear(1) }
    MAX-ACCESS  read-write
    STATUS      current
    DESCRIPTION "Set to clear(1) to clear the entire list/table of trusted devices which bypass parental controls."
    ::= { arrisRouterFWParentalControls 8 }


arrisRouterKeywordTableFreeIdx OBJECT-TYPE
    SYNTAX      Integer32
    MAX-ACCESS  read-only
    STATUS      current
    DESCRIPTION "The lowest available index to that may be used to add a row instance to the arrisRouterKeywordBlkTable."
    ::= { arrisRouterFWParentalControls 9 }


arrisRouterKeywordBlkTable  OBJECT-TYPE
    SYNTAX      SEQUENCE OF ArrisRouterKeywordBlkEntry
    MAX-ACCESS  not-accessible
    STATUS      current
    DESCRIPTION "A table of keywords to block when web surfing."
    ::= { arrisRouterFWParentalControls 10 }

arrisRouterKeywordBlkEntry OBJECT-TYPE
    SYNTAX      ArrisRouterKeywordBlkEntry
    MAX-ACCESS  not-accessible
    STATUS      current
	DESCRIPTION "A table of keywords to block when web surfing."
    INDEX   { arrisRouterKeywordBlkIndex }
    ::= { arrisRouterKeywordBlkTable 1 }

ArrisRouterKeywordBlkEntry ::=
    SEQUENCE    {
                arrisRouterKeywordBlkIndex		Integer32,
                arrisRouterKeywordBlkWord		DisplayString,
                arrisRouterKeywordBlkTOD		Integer32,
                arrisRouterKeywordBlkStatus		RowStatus,
                arrisRouterKeywordBlkStartMin		INTEGER,
                arrisRouterKeywordBlkEndMin		INTEGER,
                arrisRouterKeywordBlkFilterTr69InstanceID		Unsigned32,
                arrisRouterKeywordBlkTimeTr69InstanceID			Unsigned32,
                arrisRouterKeywordBlkTimeTr69LastInstance		Unsigned32
    }

arrisRouterKeywordBlkIndex OBJECT-TYPE
    SYNTAX      Integer32 (1..50)
    MAX-ACCESS  not-accessible
    STATUS      current
    DESCRIPTION "Indicates the instance of this table row."
    ::= { arrisRouterKeywordBlkEntry 1 }

arrisRouterKeywordBlkWord OBJECT-TYPE
    SYNTAX      DisplayString (SIZE (1..32))
    MAX-ACCESS  read-create
    STATUS      current
    DESCRIPTION "The keyword to block."
    ::= { arrisRouterKeywordBlkEntry 2 }

arrisRouterKeywordBlkTOD OBJECT-TYPE
    SYNTAX      Integer32
    MAX-ACCESS  read-create
    STATUS      current
    DESCRIPTION  "This is a 32-bit bitmask that sets the time of day to apply and days of the week to apply this rule.
                Bits 0-6 correspond to Sunday-Saturday.  Set the bit high (1) to enable this rule for the day of the week.
                Bits 7-30 apply to hours of the day 00:00:00-23:00:00.  Each it corresponds to an hour.  Set the bit high to
                enable the rule for specified hour."
    ::= { arrisRouterKeywordBlkEntry 3 }

arrisRouterKeywordBlkStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterKeywordBlkStatus column is 'notReady'.

         Only rows with a status of active(1) will be applied."
    ::= { arrisRouterKeywordBlkEntry 4 }

arrisRouterKeywordBlkStartMin OBJECT-TYPE
    SYNTAX     INTEGER
    MAX-ACCESS  read-create
    STATUS      current
    DESCRIPTION  "start minute means minutes counting from 00:00 each day (range:0~1439), eg. 02:30 expressed 150 mins"
    ::= { arrisRouterKeywordBlkEntry 5 }

arrisRouterKeywordBlkEndMin OBJECT-TYPE
    SYNTAX     INTEGER
    MAX-ACCESS  read-create
    STATUS      current
    DESCRIPTION  "end minute means minutes counting from 00:00 each day (range:0~1439), eg. 02:30 expressed 150 mins"
    ::= { arrisRouterKeywordBlkEntry 6 }

arrisRouterKeywordBlkFilterTr69InstanceID OBJECT-TYPE
    SYNTAX      Unsigned32
    MAX-ACCESS  read-create
    STATUS      current
    DESCRIPTION  "The rule instance mapping for Device.X_ARRIS_COM_Firewall.ParentalControls.KeywordFilter.{i}."
    ::= { arrisRouterKeywordBlkEntry 7 }

arrisRouterKeywordBlkTimeTr69InstanceID OBJECT-TYPE
    SYNTAX      Unsigned32
    MAX-ACCESS  read-create
    STATUS      current
    DESCRIPTION  "The time instance mapping for Device.X_ARRIS_COM_Firewall.ParentalControls.KeywordFilter.{i}.Day.{i}.Time.{i}."
    ::= { arrisRouterKeywordBlkEntry 8 }

arrisRouterKeywordBlkTimeTr69LastInstance OBJECT-TYPE
    SYNTAX      Unsigned32
    MAX-ACCESS  read-write
    STATUS      current
    DESCRIPTION "A count indicates that how many instance TR-069 is created under Device.X_ARRIS_COM_Firewall.ParentalControls.KeywordFilter.{i}.Day.{i}.Time.{i}."
    ::= { arrisRouterKeywordBlkEntry 9 }

arrisRouterBlackListFreeIdx OBJECT-TYPE
    SYNTAX      Integer32
    MAX-ACCESS  read-only
    STATUS      current
    DESCRIPTION "The lowest available index to that may be used to add a row instance to the arrisRouterBlackListTable."
    ::= { arrisRouterFWParentalControls 11 }

arrisRouterBlackListTable  OBJECT-TYPE
    SYNTAX      SEQUENCE OF ArrisRouterBlackListEntry
    MAX-ACCESS  not-accessible
    STATUS      current
    DESCRIPTION "A table of domain names to block when web surfing."
    ::= { arrisRouterFWParentalControls 12 }

arrisRouterBlackListEntry OBJECT-TYPE
    SYNTAX      ArrisRouterBlackListEntry
    MAX-ACCESS  not-accessible
    STATUS      current
	DESCRIPTION "A table of domain names to block when web surfing."
    INDEX   { arrisRouterBlackListIndex }
    ::= { arrisRouterBlackListTable 1 }

ArrisRouterBlackListEntry ::=
    SEQUENCE    {
                arrisRouterBlackListIndex		Integer32,
                arrisRouterBlackListDomain              DisplayString,
                arrisRouterBlackListTOD			Integer32,
                arrisRouterBlackListStatus		RowStatus,
                arrisRouterBlackListStartMin		INTEGER,
                arrisRouterBlackListEndMin		INTEGER,
                arrisRouterBlackListWebSiteTr69InstanceID		Unsigned32,
                arrisRouterBlackListTimeTr69InstanceID			Unsigned32,
                arrisRouterBlackListTimeTr69LastInstance		Unsigned32
    }

arrisRouterBlackListIndex OBJECT-TYPE
    SYNTAX      Integer32 (1..16)
    MAX-ACCESS  not-accessible
    STATUS      current
    DESCRIPTION "Indicates the instance of this table row."
    ::= { arrisRouterBlackListEntry 1 }

arrisRouterBlackListDomain OBJECT-TYPE
    SYNTAX      DisplayString (SIZE (0..64))
    MAX-ACCESS  read-create
    STATUS      current
    DESCRIPTION "The domain to alway block - black listed."
    ::= { arrisRouterBlackListEntry 2 }

arrisRouterBlackListTOD OBJECT-TYPE
    SYNTAX      Integer32
    MAX-ACCESS  read-create
    STATUS      current
    DESCRIPTION  "This is a 32-bit bitmask that sets the time of day to apply and days of the week to apply this rule.
                Bits 0-6 correspond to Sunday-Saturday.  Set the bit high (1) to enable this rule for the day of the week.
                Bits 7-30 apply to hours of the day 00:00:00-23:00:00.  Each it corresponds to an hour.  Set the bit high to
                enable the rule for specified hour."
    ::= { arrisRouterBlackListEntry 3 }

arrisRouterBlackListStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterBlackListStatus column is 'notReady'.

         Only rows with a status of active(1) will be applied."
    ::= { arrisRouterBlackListEntry 4 }

arrisRouterBlackListStartMin OBJECT-TYPE
    SYNTAX     INTEGER
    MAX-ACCESS  read-create
    STATUS      current
    DESCRIPTION  "start minute means minutes counting from 00:00 each day (range:0~1439), eg. 02:30 expressed 150 mins"
    ::= { arrisRouterBlackListEntry 5 }

arrisRouterBlackListEndMin OBJECT-TYPE
    SYNTAX     INTEGER
    MAX-ACCESS  read-create
    STATUS      current
    DESCRIPTION  "end minute means minutes counting from 00:00 each day (range:0~1439), eg. 02:30 expressed 150 mins"
    ::= { arrisRouterBlackListEntry 6 }

arrisRouterBlackListWebSiteTr69InstanceID OBJECT-TYPE
    SYNTAX      Unsigned32
    MAX-ACCESS  read-create
    STATUS      current
    DESCRIPTION  "The rule instance mapping for Device.X_ARRIS_COM_Firewall.ParentalControls.WebSiteDenyList.{i}."
    ::= { arrisRouterBlackListEntry 7 }

arrisRouterBlackListTimeTr69InstanceID OBJECT-TYPE
    SYNTAX      Unsigned32
    MAX-ACCESS  read-create
    STATUS      current
    DESCRIPTION  "The time instance mapping for Device.X_ARRIS_COM_Firewall.ParentalControls.WebSiteDenyList.{i}.Day.{i}.Time.{i}."
    ::= { arrisRouterBlackListEntry 8 }

arrisRouterBlackListTimeTr69LastInstance OBJECT-TYPE
    SYNTAX      Unsigned32
    MAX-ACCESS  read-write
    STATUS      current
    DESCRIPTION "A count indicates that how many instance TR-069 is created under Device.X_ARRIS_COM_Firewall.ParentalControls.WebSiteDenyList.{i}.Day.{i}.Time.{i}."
    ::= { arrisRouterBlackListEntry 9 }

arrisRouterWhiteListFreeIdx OBJECT-TYPE
    SYNTAX      Integer32
    MAX-ACCESS  read-only
    STATUS      current
    DESCRIPTION "The lowest available index to that may be used to add a row instance to the arrisRouterWhiteListTable."
    ::= { arrisRouterFWParentalControls 13 }


arrisRouterWhiteListTable  OBJECT-TYPE
    SYNTAX      SEQUENCE OF ArrisRouterWhiteListEntry
    MAX-ACCESS  not-accessible
    STATUS      current
    DESCRIPTION "A table of domains to NEVER block when web surfing."
    ::= { arrisRouterFWParentalControls 14 }

arrisRouterWhiteListEntry OBJECT-TYPE
    SYNTAX      ArrisRouterWhiteListEntry
    MAX-ACCESS  not-accessible
    STATUS      current
	DESCRIPTION "A table of domains to NEVER block when web surfing."
    INDEX   { arrisRouterWhiteListIndex }
    ::= { arrisRouterWhiteListTable 1 }

ArrisRouterWhiteListEntry ::=
    SEQUENCE    {
                arrisRouterWhiteListIndex		Integer32,
                arrisRouterWhiteListDomain  	DisplayString,
                arrisRouterWhiteListTOD			Integer32,
                arrisRouterWhiteListStatus		RowStatus,
                arrisRouterWhiteListWebSiteTr69InstanceID		Unsigned32,
                arrisRouterWhiteListTimeTr69InstanceID			Unsigned32,
                arrisRouterWhiteListTimeTr69LastInstance		Unsigned32
    }

arrisRouterWhiteListIndex OBJECT-TYPE
    SYNTAX      Integer32 (1..16)
    MAX-ACCESS  not-accessible
    STATUS      current
    DESCRIPTION "Indicates the instance of this table row."
    ::= { arrisRouterWhiteListEntry 1 }

arrisRouterWhiteListDomain OBJECT-TYPE
    SYNTAX      DisplayString (SIZE (0..64))
    MAX-ACCESS  read-create
    STATUS      current
    DESCRIPTION "The domain to alway allow - White listed."
    ::= { arrisRouterWhiteListEntry 2 }

arrisRouterWhiteListTOD OBJECT-TYPE
    SYNTAX      Integer32
    MAX-ACCESS  read-write
    STATUS      current
    DESCRIPTION  "This is a 32-bit bitmask that sets the time of day to apply and days of the week to apply this rule.
                Bits 0-6 correspond to Sunday-Saturday.  Set the bit high (1) to enable this rule for the day of the week.
                Bits 7-30 apply to hours of the day 00:00:00-23:00:00.  Each it corresponds to an hour.  Set the bit high to
                enable the rule for specified hour."
    ::= { arrisRouterWhiteListEntry 3 }

arrisRouterWhiteListStatus OBJECT-TYPE
    SYNTAX      RowStatus
    MAX-ACCESS  read-create
    STATUS      current
    DESCRIPTION
        "The status of this conceptual row.
         To create a row in this table, a manager must set this object to
         either createAndGo(4) or createAndWait(5).
         Until instances of all corresponding columns are appropriately
         configured, the value of the corresponding instance of the
         arrisRouterWhiteListStatus column is 'notReady'.
         Only rows with a status of active(1) will be applied."
    ::= { arrisRouterWhiteListEntry 4 }

arrisRouterWhiteListWebSiteTr69InstanceID OBJECT-TYPE
    SYNTAX      Unsigned32
    MAX-ACCESS  read-create
    STATUS      current
    DESCRIPTION  "The rule instance mapping for Device.X_ARRIS_COM_Firewall.ParentalControls.WebSiteAllowList.{i}."
    ::= { arrisRouterWhiteListEntry 5 }

arrisRouterWhiteListTimeTr69InstanceID OBJECT-TYPE
    SYNTAX      Unsigned32
    MAX-ACCESS  read-create
    STATUS      current
    DESCRIPTION  "The time instance mapping for Device.X_ARRIS_COM_Firewall.ParentalControls.WebSiteAllowList.{i}.Day.{i}.Time.{i}."
    ::= { arrisRouterWhiteListEntry 6 }

arrisRouterWhiteListTimeTr69LastInstance OBJECT-TYPE
    SYNTAX      Unsigned32
    MAX-ACCESS  read-write
    STATUS      current
    DESCRIPTION "A count indicates that how many instance TR-069 is created under Device.X_ARRIS_COM_Firewall.ParentalControls.WebSiteAllowList.{i}.Day.{i}.Time.{i}."
    ::= { arrisRouterWhiteListEntry 7 }

arrisRouterTrustedDeviceFreeIdx OBJECT-TYPE
    SYNTAX      Integer32
    MAX-ACCESS  read-only
    STATUS      current
    DESCRIPTION "The lowest available index to that may be used to add a row instance to the arrisRouterTrustedDeviceTable."
    ::= { arrisRouterFWParentalControls 15 }

arrisRouterTrustedDeviceTable  OBJECT-TYPE
    SYNTAX      SEQUENCE OF ArrisRouterTrustedDeviceEntry
    MAX-ACCESS  not-accessible
    STATUS      current
    DESCRIPTION "A table of trusted devices which bypass parental controls."
    ::= { arrisRouterFWParentalControls 16 }

arrisRouterTrustedDeviceEntry OBJECT-TYPE
    SYNTAX      ArrisRouterTrustedDeviceEntry
    MAX-ACCESS  not-accessible
    STATUS      current
    DESCRIPTION "A table of trusted devices which bypass parental controls."
    INDEX   { arrisRouterTrustedDeviceIndex }
    ::= { arrisRouterTrustedDeviceTable 1 }

ArrisRouterTrustedDeviceEntry ::=
    SEQUENCE    {
                arrisRouterTrustedDeviceIndex		Integer32,
                arrisRouterTrustedDeviceMAC  		MacAddress,
                arrisRouterTrustedDeviceStatus		RowStatus,
                arrisRouterTrustedDeviceName		DisplayString,
                arrisRouterTrustedDeviceAddrType	InetAddressType,
                arrisRouterTrustedDeviceAddr		InetAddress,
                arrisRouterTrustedDeviceTr69InstanceID  Unsigned32
    }

arrisRouterTrustedDeviceIndex OBJECT-TYPE
    SYNTAX      Integer32 (1..30)
    MAX-ACCESS  not-accessible
    STATUS      current
    DESCRIPTION "Indicates the instance of this table row.
                 NOTE: For TS7.x, this mib only supports (1..3)."
    ::= { arrisRouterTrustedDeviceEntry 1 }

arrisRouterTrustedDeviceMAC OBJECT-TYPE
    SYNTAX      MacAddress
    MAX-ACCESS  read-create
    STATUS      current
    DESCRIPTION "The MAC address of a device on the local network that bypasses parental controls."
    ::= { arrisRouterTrustedDeviceEntry 2 }

arrisRouterTrustedDeviceStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterTrustedDeviceStatus column is 'notReady'.

         Only rows with a status of active(1) will be applied."
    ::= { arrisRouterTrustedDeviceEntry 3 }

arrisRouterTrustedDeviceName OBJECT-TYPE
    SYNTAX      DisplayString
    MAX-ACCESS  read-create
    STATUS      current
    DESCRIPTION "The name of a device on the local network that bypasses parental controls."
    ::= { arrisRouterTrustedDeviceEntry 4 }

arrisRouterTrustedDeviceAddrType OBJECT-TYPE
    SYNTAX      InetAddressType
    MAX-ACCESS  read-create
    STATUS      current
    DESCRIPTION "IP address type for a device on the local network that bypasses parental controls."
    ::= { arrisRouterTrustedDeviceEntry 5 }

arrisRouterTrustedDeviceAddr OBJECT-TYPE
    SYNTAX      InetAddress
    MAX-ACCESS  read-create
    STATUS      current
    DESCRIPTION "IP address for a device on the local network that bypasses parental controls."
    ::= { arrisRouterTrustedDeviceEntry 6 }

arrisRouterTrustedDeviceTr69InstanceID OBJECT-TYPE
    SYNTAX      Unsigned32
    MAX-ACCESS  read-create
    STATUS      current
    DESCRIPTION  "The rule instance mapping for Device.X_ARRIS_COM_Firewall.ParentalControls.TrustedMAC.{i}."
    ::= { arrisRouterTrustedDeviceEntry 7 }

arrisRouterEnableParentalCont OBJECT-TYPE
    SYNTAX      TruthValue
    MAX-ACCESS  read-write
    STATUS      current
    DESCRIPTION "Enable/disable parental controls."
	DEFVAL { false }
    ::= { arrisRouterFWParentalControls 17 }

arrisRouterManagedSitesEnabled OBJECT-TYPE
    SYNTAX      TruthValue
    MAX-ACCESS  read-write
    STATUS      current
    DESCRIPTION "Indicates whether parental controls' 'Managed Sites' are enabled."
	DEFVAL { false }
    ::= { arrisRouterFWParentalControls 18 }

arrisRouterManagedServicesEnabled OBJECT-TYPE
    SYNTAX      TruthValue
    MAX-ACCESS  read-write
    STATUS      current
    DESCRIPTION "Indicates whether parental controls' 'Managed Services' are enabled."
	DEFVAL { false }
    ::= { arrisRouterFWParentalControls 19 }

arrisRouterManagedDevicesEnabled OBJECT-TYPE
    SYNTAX      TruthValue
    MAX-ACCESS  read-write
    STATUS      current
    DESCRIPTION "Indicates whether parental controls' 'Managed Devices' are enabled."
	DEFVAL { false }
    ::= { arrisRouterFWParentalControls 20 }

arrisRouterTrustedDeviceManagedServicesTable  OBJECT-TYPE
    SYNTAX      SEQUENCE OF ArrisRouterTrustedDeviceManagedServicesEntry
    MAX-ACCESS  not-accessible
    STATUS      current
    DESCRIPTION "A table of trusted devices which bypasses parental controls' services' settings."
    ::= { arrisRouterFWParentalControls 21 }

arrisRouterTrustedDeviceManagedServicesEntry OBJECT-TYPE
    SYNTAX      ArrisRouterTrustedDeviceManagedServicesEntry
    MAX-ACCESS  not-accessible
    STATUS      current
	DESCRIPTION "A table of trusted devices which bypasses parental controls' services' settings."
    INDEX   { arrisRouterTrustedDeviceManagedServicesIndex }
    ::= { arrisRouterTrustedDeviceManagedServicesTable 1 }

ArrisRouterTrustedDeviceManagedServicesEntry ::=
    SEQUENCE    {
                arrisRouterTrustedDeviceManagedServicesIndex		Integer32,
                arrisRouterTrustedDeviceManagedServicesMAC  		MacAddress,
                arrisRouterTrustedDeviceManagedServicesStatus		RowStatus,
		arrisRouterTrustedDeviceManagedServicesName		DisplayString,
		arrisRouterTrustedDeviceManagedServicesAddrType		InetAddressType,
		arrisRouterTrustedDeviceManagedServicesAddr		InetAddress
    }

arrisRouterTrustedDeviceManagedServicesIndex OBJECT-TYPE
    SYNTAX      Integer32 (1..30)
    MAX-ACCESS  not-accessible
    STATUS      current
    DESCRIPTION "Indicates the instance of this table row.
                 NOTE: For TS7.x, this mib only supports (1..3)."
    ::= { arrisRouterTrustedDeviceManagedServicesEntry 1 }

arrisRouterTrustedDeviceManagedServicesMAC OBJECT-TYPE
    SYNTAX      MacAddress
    MAX-ACCESS  read-create
    STATUS      current
    DESCRIPTION "The MAC address of a device on the local network that bypasses parental controls' services' settings."
    ::= { arrisRouterTrustedDeviceManagedServicesEntry 2 }

arrisRouterTrustedDeviceManagedServicesStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterTrustedDeviceManagedServicesStatus column is 'notReady'.

         Only rows with a status of active(1) will be applied."
    ::= { arrisRouterTrustedDeviceManagedServicesEntry 3 }

arrisRouterTrustedDeviceManagedServicesName OBJECT-TYPE
    SYNTAX      DisplayString
    MAX-ACCESS  read-create
    STATUS      current
    DESCRIPTION "The name of a device on the local network that bypasses parental controls' services' settings."
    ::= { arrisRouterTrustedDeviceManagedServicesEntry 4 }

arrisRouterTrustedDeviceManagedServicesAddrType OBJECT-TYPE
    SYNTAX      InetAddressType
    MAX-ACCESS  read-create
    STATUS      current
    DESCRIPTION "IP address type for a device on the local network that bypasses parental controls' services' settings."
    ::= { arrisRouterTrustedDeviceManagedServicesEntry 5 }

arrisRouterTrustedDeviceManagedServicesAddr OBJECT-TYPE
    SYNTAX      InetAddress
    MAX-ACCESS  read-create
    STATUS      current
    DESCRIPTION "IP address for a device on the local network that bypasses parental controls services."
    ::= { arrisRouterTrustedDeviceManagedServicesEntry 6 }


arrisRouterListActiveType  OBJECT-TYPE
    SYNTAX      INTEGER { blackList(1), whiteList(2) }
    MAX-ACCESS  read-write
    STATUS      current
    DESCRIPTION "Current active list type. Default value is Black List."
    DEFVAL { 1 }
    ::= { arrisRouterFWParentalControls 22 }

arrisRouterExceptionListCount  OBJECT-TYPE
    SYNTAX      Integer32
    MAX-ACCESS  read-only
    STATUS      current
    DESCRIPTION "Current count of Exception listed domain."
    ::= { arrisRouterFWParentalControls 24 }

arrisRouterExceptionListTable  OBJECT-TYPE
    SYNTAX      SEQUENCE OF ArrisRouterExceptionListEntry
    MAX-ACCESS  not-accessible
    STATUS      current
    DESCRIPTION "A table of domains to NEVER block when web surfing."
    ::= { arrisRouterFWParentalControls 25 }

arrisRouterExceptionListEntry OBJECT-TYPE
    SYNTAX      ArrisRouterExceptionListEntry
    MAX-ACCESS  not-accessible
    STATUS      current
    DESCRIPTION "A table of domains to NEVER block when web surfing."
    INDEX   { arrisRouterExceptionListIndex }
    ::= { arrisRouterExceptionListTable 1 }

ArrisRouterExceptionListEntry ::=
    SEQUENCE    {
                arrisRouterExceptionListIndex               Integer32,
                arrisRouterExceptionListDomain              DisplayString,
                arrisRouterExceptionListStatus              RowStatus
    }

arrisRouterExceptionListIndex OBJECT-TYPE
    SYNTAX      Integer32 (1..30)
    MAX-ACCESS  not-accessible
    STATUS      current
    DESCRIPTION "Indicates the instance of this table row."
    ::= { arrisRouterExceptionListEntry 1 }

arrisRouterExceptionListDomain OBJECT-TYPE
    SYNTAX      DisplayString (SIZE (0..64))
    MAX-ACCESS  read-create
    STATUS      current
    DESCRIPTION "The domain to allow which is blocked by keyword - Exception listed."
    ::= { arrisRouterExceptionListEntry 2 }

arrisRouterExceptionListStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterExceptionListStatus column is 'notReady'.

         Only rows with a status of active(1) will be applied."
    ::= { arrisRouterExceptionListEntry 3 }

arrisRouterKeywordBlkFilterTr69LastInstance OBJECT-TYPE
    SYNTAX      Unsigned32
    MAX-ACCESS  read-write
    STATUS      current
    DESCRIPTION "A count indicates that how many instance TR-069 is created under Device.X_ARRIS_COM_Firewall.ParentalControls.KeywordFilter.{i}."
    ::= { arrisRouterFWParentalControls 26 }

arrisRouterBlackListWebSiteTr69LastInstance OBJECT-TYPE
    SYNTAX      Unsigned32
    MAX-ACCESS  read-write
    STATUS      current
    DESCRIPTION "A count indicates that how many instance TR-069 is created under Device.X_ARRIS_COM_Firewall.ParentalControls.WebSiteDenyList.{i}."
    ::= { arrisRouterFWParentalControls 27 }

arrisRouterWhiteListWebSiteTr69LastInstance OBJECT-TYPE
    SYNTAX      Unsigned32
    MAX-ACCESS  read-write
    STATUS      current
    DESCRIPTION "A count indicates that how many instance TR-069 is created under Device.X_ARRIS_COM_Firewall.ParentalControls.WebSiteAllowList.{i}."
    ::= { arrisRouterFWParentalControls 28 }

arrisRouterTrustedDeviceTr69LastInstance OBJECT-TYPE
    SYNTAX      Unsigned32
    MAX-ACCESS  read-write
    STATUS      current
    DESCRIPTION "A count indicates that how many instance TR-069 is created under Device.X_ARRIS_COM_Firewall.ParentalControls.TrustedMAC.{i}."
    ::= { arrisRouterFWParentalControls 29 }

arrisRouterFWAllowICMP OBJECT-TYPE
    SYNTAX      TruthValue
    MAX-ACCESS  read-write
    STATUS      current
    DESCRIPTION "Specify to allow or not allow ICMP messages such as Ping and trace route."
    DEFVAL { true }
    ::= { arrisRouterFWCfg 21 }

arrisRouterFWResetDefaults OBJECT-TYPE
    SYNTAX      TruthValue
    MAX-ACCESS  read-write
    STATUS      current
    DESCRIPTION "Reset Firewall settings (only) to default values."
    ::= { arrisRouterFWCfg 22 }

arrisRouterFWBlockHTTP OBJECT-TYPE
    SYNTAX      TruthValue
    MAX-ACCESS  read-write
    STATUS      current
    DESCRIPTION  "Enable/disable blocking of incoming HTTP traffic."
    ::= { arrisRouterFWCfg 23 }

arrisRouterFWBlockP2P OBJECT-TYPE
    SYNTAX      TruthValue
    MAX-ACCESS  read-write
    STATUS      current
    DESCRIPTION  "Enable/disable blocking of peer-to-peer applications."
    ::= { arrisRouterFWCfg 24 }

arrisRouterFWBlockIdent OBJECT-TYPE
    SYNTAX      TruthValue
    MAX-ACCESS  read-write
    STATUS      current
    DESCRIPTION  "Enable/disable blocking of Ident protocol."
    ::= { arrisRouterFWCfg 25 }

arrisRouterFWBlockICMP OBJECT-TYPE
    SYNTAX      TruthValue
    MAX-ACCESS  read-write
    STATUS      current
    DESCRIPTION "Specify to allow or not block ICMP messages such as Ping and trace route."
    DEFVAL { false }
    ::= { arrisRouterFWCfg 26 }

arrisRouterFWBlockMulticast OBJECT-TYPE
    SYNTAX      TruthValue
    MAX-ACCESS  read-write
    STATUS      current
    DESCRIPTION  "Enable/disable blocking of multicast traffic."
    DEFVAL { false }
    ::= { arrisRouterFWCfg 27 }

arrisRouterFWVSSrcPortExclude OBJECT-TYPE
    SYNTAX      DisplayString (SIZE (0..255))
    MAX-ACCESS  read-write
    STATUS      deprecated
    DESCRIPTION "A delimited list of ports not allowed to be configured as source ports for port forwarding.
                This defines illegal values for: arrisRouterFWVirtSrvPortStart and arrisRouterFWVirtSrvPortEnd.
                The string should be delimited with ','
                i.e. 80,100,102,200"
    ::= { arrisRouterFWCfg 28 }

arrisRouterFWVSDestPortExclude OBJECT-TYPE
    SYNTAX      DisplayString (SIZE (0..255))
    MAX-ACCESS  read-write
    STATUS      deprecated
    DESCRIPTION "A delimited list of ports not allowed to be configured as local destination ports for port forwarding.
                This defines illegal values for: arrisRouterFWVirtSrvLocalPortStart and arrisRouterFWVirtSrvLocalPortEnd.
                The string should be delimited with ','
                i.e. 80,100,102,200"
    ::= { arrisRouterFWCfg 29 }

arrisRouterFWEnableNow OBJECT-TYPE
    SYNTAX      TruthValue
    MAX-ACCESS  read-write
    STATUS      current
    DESCRIPTION "Enable or disable the firewall immediately without requiring an 'apply'"
    DEFVAL { true }
    ::= { arrisRouterFWCfg 30 }

arrisRouterFWAllowDestPorts OBJECT-TYPE
    SYNTAX      DisplayString (SIZE (0..255))
    MAX-ACCESS  read-write
    STATUS      deprecated
    DESCRIPTION "A delimited list of destination ports that are always allowed when the source destination is the eRouter itself.
                This is, at this time, exclusively for the Media Gatewy product (MG5xxx)
                i.e. 80,100,102,200"
    ::= { arrisRouterFWCfg 31 }

arrisRouterFWVirtSrvTableEnabled OBJECT-TYPE
    SYNTAX      TruthValue
    MAX-ACCESS  read-write
    STATUS      current
    DESCRIPTION "Indicates whether Port Forwarding is enabled."
    DEFVAL { true }
    ::= { arrisRouterFWCfg 32 }

arrisRouterFWPortTrigTableEnabled OBJECT-TYPE
    SYNTAX      TruthValue
    MAX-ACCESS  read-write
    STATUS      current
    DESCRIPTION "Indicates whether port triggering is enabled."
    DEFVAL { true }
    ::= { arrisRouterFWCfg 33 }

arrisRouterFWPortForward OBJECT-TYPE
    SYNTAX      DisplayString (SIZE (0..255))
    MAX-ACCESS  read-write
    STATUS      current
    DESCRIPTION "A convenience method for internal applications to add port forwarding similar to the UPnP method.
                 Port forwarding entries added this way are not persisted.
                 To add a port to a local device use the format: IP=192.168.0.4;NAME=FooBar;GLOBALPORT=9888-9888;LOCALPORT=8765-8765;PROTO=TCP;
                 To let the Arris Media Gateway automatically assign the ports use: IP=192.168.0.4;NAME=FooBar;PROTO=TCP;
                 Note that PROTO=XXX where XXX is either TCP, UDP, or BOTH."
    ::= { arrisRouterFWCfg 34 }

arrisRouterFWPortForwardStatus OBJECT-TYPE
	SYNTAX      DisplayString (SIZE (0..255))
    MAX-ACCESS  read-only
    STATUS      current
    DESCRIPTION "Returns the status of any port forwards added using arrisRouterFWPortForward.
                 Format is: FooBar=9888,8765;BarFoo=8777-8778,9888-9889;"
    ::= { arrisRouterFWCfg 35 }

arrisRouterFWPortForwardDelete OBJECT-TYPE
	SYNTAX      DisplayString (SIZE (0..255))
    MAX-ACCESS  read-write
    STATUS      current
    DESCRIPTION "A convenience method for internal applications to remove port forwarding that was added using arrisRouterFWPortForward.
				To remove port forwards that match a name, use the format: NAME=FooBar."
    ::= { arrisRouterFWCfg 36 }

arrisRouterFWExceptionList OBJECT-TYPE
	SYNTAX      DisplayString (SIZE (0..255))
    MAX-ACCESS  read-write
    STATUS      current
    DESCRIPTION "A string used to configure IP addresses and ports to allow thru the firewall.
				 Format: IP/PREFIX:PORT;IP2/PREFIX2:PORT2"
    ::= { arrisRouterFWCfg 37 }

arrisRouterFWIP2AddrTypeDMZ OBJECT-TYPE
    SYNTAX      InetAddressType
    MAX-ACCESS  read-write
    STATUS      current
    DESCRIPTION  "The second IP address type of the DMZ host"
    ::= { arrisRouterFWCfg 38 }

arrisRouterFWIP2AddrDMZ OBJECT-TYPE
    SYNTAX      InetAddress
    MAX-ACCESS  read-write
    STATUS      current
    DESCRIPTION  "The second IP address of the DMZ host"
    ::= { arrisRouterFWCfg 39 }

arrisRouterFWIPv6Security      OBJECT IDENTIFIER ::= { arrisRouterFWCfg 40 }

arrisRouterFWIPv6SecurityLevel OBJECT-TYPE
    SYNTAX INTEGER { minimum(1), medium(2), maximum(3), custom(4) }
    MAX-ACCESS  read-write
    STATUS      current
    DESCRIPTION "IPv6 Firewall security level.
                 NOTE: For customer Comcast, value 1 represents default(1), NOT minimum(1)."
    ::= { arrisRouterFWIPv6Security 1 }

arrisRouterFWIPv6BlockHTTP OBJECT-TYPE
    SYNTAX      TruthValue
    MAX-ACCESS  read-write
    STATUS      current
    DESCRIPTION "For IPv6 custom security level, Enable/disable blocking of incoming HTTP traffic."
    DEFVAL { false }
    ::= { arrisRouterFWIPv6Security 2 }

arrisRouterFWIPv6BlockICMP OBJECT-TYPE
    SYNTAX      TruthValue
    MAX-ACCESS  read-write
    STATUS      current
    DESCRIPTION "For IPv6 custom security level, Enable/disable blocking of incoming HTTP traffic."
    DEFVAL { false }
    ::= { arrisRouterFWIPv6Security 3 }

arrisRouterFWIPv6BlockMulticast OBJECT-TYPE
    SYNTAX      TruthValue
    MAX-ACCESS  read-write
    STATUS      current
    DESCRIPTION "For IPv6 custom security level, Enable/disable blocking of multicast traffic."
    DEFVAL { false }
    ::= { arrisRouterFWIPv6Security 4 }

arrisRouterFWIPv6BlockP2P OBJECT-TYPE
    SYNTAX      TruthValue
    MAX-ACCESS  read-write
    STATUS      current
    DESCRIPTION "For IPv6 custom security level, Enable/disable blocking of peer-to-peer applications."
    DEFVAL { false }
    ::= { arrisRouterFWIPv6Security 5 }

arrisRouterFWIPv6BlockIDENT OBJECT-TYPE
    SYNTAX      TruthValue
    MAX-ACCESS  read-write
    STATUS      current
    DESCRIPTION "For IPv6 custom security level, Enable/disable blocking of Ident protocol."
    DEFVAL { false }
    ::= { arrisRouterFWIPv6Security 6 }

arrisRouterFWIPv6Enable OBJECT-TYPE
    SYNTAX      TruthValue
    MAX-ACCESS  read-write
    STATUS      current
    DESCRIPTION "Is the IPv6 firewall enabled or not"
    DEFVAL { true }
    ::= { arrisRouterFWIPv6Security 7 }

arrisRouterFWIPv6ResetDefaults OBJECT-TYPE
    SYNTAX      TruthValue
    MAX-ACCESS  read-write
    STATUS      current
    DESCRIPTION "Reset IPv6 Firewall settings (only) to default values."
    ::= { arrisRouterFWIPv6Security 8 }

arrisRouterFWIPv6BlockMtaICMPNS OBJECT-TYPE
    SYNTAX      TruthValue
    MAX-ACCESS  read-write
    STATUS      current
    DESCRIPTION "For IPv6 custom security level, Enable/disable blocking of incoming ICMP Neighbour Solicitation for MTA ."
    DEFVAL { false }
    ::= { arrisRouterFWIPv6Security 9 }

arrisRouterFWMacBridgingWebPageEnabled OBJECT-TYPE
    SYNTAX      TruthValue
    MAX-ACCESS  read-write
    STATUS      current
    DESCRIPTION "Indicates whether MAC bridging web page displays for admin users."
	DEFVAL { false }
    ::= { arrisRouterFWCfg 41 }

arrisRouterFWMacBridgingFunctionEnabled OBJECT-TYPE
    SYNTAX      TruthValue
    MAX-ACCESS  read-write
    STATUS      current
    DESCRIPTION "Indicates whether MAC bridging function is enabled."
	DEFVAL { false }
    ::= { arrisRouterFWCfg 42 }

arrisRouterFWMacBridgingTable OBJECT-TYPE
    SYNTAX      SEQUENCE OF ArrisRouterFWMacBridgingEntry
    MAX-ACCESS  not-accessible
    STATUS      current
    DESCRIPTION  "A table of bridged device MAC addresses. Packets from or to these MACs are bridged directly from LAN to WAN, bypassing the normal routing."
    ::= {  arrisRouterFWCfg 43 }

arrisRouterFWMacBridgingEntry OBJECT-TYPE
    SYNTAX      ArrisRouterFWMacBridgingEntry
    MAX-ACCESS  not-accessible
    STATUS      current
    DESCRIPTION  "A table of MAC addresses. Device of  these MACs  in LAN are bridged directly from LAN to WAN, bypassing the normal routing."
    INDEX {arrisRouterFWMacBridgingIndex }
    ::= { arrisRouterFWMacBridgingTable 1 }

ArrisRouterFWMacBridgingEntry ::= SEQUENCE {
    arrisRouterFWMacBridgingIndex         INTEGER,
    arrisRouterFWMacBridgingName         DisplayString,
    arrisRouterFWMacBridgingMACAddr       MacAddress,
    arrisRouterFWMacBridgingRowStatus     RowStatus
    }

arrisRouterFWMacBridgingIndex OBJECT-TYPE
    SYNTAX  INTEGER (1..6)
    MAX-ACCESS  not-accessible
    STATUS  current
    DESCRIPTION  "The index into the Mac Bridging table."
    ::= {arrisRouterFWMacBridgingEntry 1 }

arrisRouterFWMacBridgingName OBJECT-TYPE
    SYNTAX      DisplayString (SIZE (0..64))
    MAX-ACCESS  read-create
    STATUS      current
    DESCRIPTION  "A textual description or name for this MAC."
    ::= { arrisRouterFWMacBridgingEntry 2 }

arrisRouterFWMacBridgingMACAddr OBJECT-TYPE
    SYNTAX  MacAddress
    MAX-ACCESS  read-create
    STATUS  current
    DESCRIPTION   "The MAC Address of LAN Device to be bridged directly from LAN to WAN."
    ::= {arrisRouterFWMacBridgingEntry 3 }

arrisRouterFWMacBridgingRowStatus OBJECT-TYPE
    SYNTAX      RowStatus
    MAX-ACCESS  read-create
    STATUS      current
    DESCRIPTION   "Row status to add/remove an arrisRouterFWMacBridgingTable entry."
    ::= { arrisRouterFWMacBridgingEntry 4 }

arrisRouterFWPortAllowTable  OBJECT-TYPE
    SYNTAX      SEQUENCE OF ArrisRouterFWPortAllowEntry
    MAX-ACCESS  not-accessible
    STATUS      current
    DESCRIPTION  "A table to allow IPV6 client to receive tcp packets with specified port"
    ::= { arrisRouterFWCfg 44 }

arrisRouterFWPortAllowEntry OBJECT-TYPE
    SYNTAX      ArrisRouterFWPortAllowEntry
    MAX-ACCESS  not-accessible
    STATUS      current
    DESCRIPTION  "A table to allow IPV6 client to receive tcp packets with specified port"
    INDEX   { arrisRouterFWPortAllowIndex }
    ::= { arrisRouterFWPortAllowTable 1 }

ArrisRouterFWPortAllowEntry ::=
    SEQUENCE    {
                arrisRouterFWPortAllowIndex Unsigned32,
                arrisRouterFWPortAllowInboundPort Unsigned32,
                arrisRouterFWPortAllowRowStatus RowStatus
                }

arrisRouterFWPortAllowIndex OBJECT-TYPE
    SYNTAX      Unsigned32
    MAX-ACCESS  not-accessible
    STATUS      current
    DESCRIPTION  "Indicates the instance of this table row."
    ::= { arrisRouterFWPortAllowEntry 1 }

arrisRouterFWPortAllowInboundPort OBJECT-TYPE
    SYNTAX      Unsigned32 (0..65535)
    MAX-ACCESS  read-write
    STATUS      current
    DESCRIPTION  "The inbound tcp port which allowed to forward to v6 client"
    ::= { arrisRouterFWPortAllowEntry 2 }

arrisRouterFWPortAllowRowStatus OBJECT-TYPE
    SYNTAX      RowStatus
    MAX-ACCESS  read-create
    STATUS      current
    DESCRIPTION  "Row status to add/remove rows"
    ::= { arrisRouterFWPortAllowEntry 3 }

arrisRouterFWDDNSExtended                         OBJECT IDENTIFIER ::= { arrisRouterFWCfg 45 }

arrisRouterFWDDNSExtendedTable OBJECT-TYPE
    SYNTAX      SEQUENCE OF ArrisRouterFWDDNSExtendedEntry
    MAX-ACCESS  not-accessible
    STATUS      current
    DESCRIPTION   "A table of dynamic DNS settings."
    ::= { arrisRouterFWDDNSExtended 1 }

arrisRouterFWDDNSExtendedEntry OBJECT-TYPE
      SYNTAX      ArrisRouterFWDDNSExtendedEntry
      MAX-ACCESS  not-accessible
      STATUS      current
      DESCRIPTION "Table contains information for dynamic DNS settings"
      INDEX { arrisRouterFWDDNSExtendedIndex }
      ::= { arrisRouterFWDDNSExtendedTable 1 }

ArrisRouterFWDDNSExtendedEntry ::= SEQUENCE {
                arrisRouterFWDDNSExtendedIndex           Unsigned32,
                arrisRouterFWDDNSExtendedEnable          TruthValue,
                arrisRouterFWDDNSExtendedType            INTEGER,
                arrisRouterFWDDNSExtendedUserName        DisplayString,
                arrisRouterFWDDNSExtendedPassword        DisplayString,
                arrisRouterFWDDNSExtendedIPAddrType      InetAddressType,
                arrisRouterFWDDNSExtendedIPAddr          InetAddress,
                arrisRouterFWDDNSExtendedStatus          DisplayString,
                arrisRouterFWDDNSExtendedRowStatus       RowStatus
                }

arrisRouterFWDDNSExtendedIndex OBJECT-TYPE
    SYNTAX      Unsigned32
    MAX-ACCESS  not-accessible
    STATUS      current
    DESCRIPTION "Index of dynamic DNS"
    ::= { arrisRouterFWDDNSExtendedEntry 1 }

arrisRouterFWDDNSExtendedEnable OBJECT-TYPE
    SYNTAX      TruthValue
    MAX-ACCESS  read-write
    STATUS      current
    DESCRIPTION  "Enable/disable dynamic DNS"
    ::= { arrisRouterFWDDNSExtendedEntry 2 }

arrisRouterFWDDNSExtendedType OBJECT-TYPE
    SYNTAX      INTEGER { unknown(0), dynDNS(1), tzo(2) }
    MAX-ACCESS  read-write
    STATUS      current
    DESCRIPTION  "Type of Dynamic DNS."
    ::= { arrisRouterFWDDNSExtendedEntry 3 }

arrisRouterFWDDNSExtendedUserName OBJECT-TYPE
    SYNTAX      DisplayString (SIZE (0..64))
    MAX-ACCESS  read-write
    STATUS      current
    DESCRIPTION  "User name to login to dynamic DNS service."
    ::= { arrisRouterFWDDNSExtendedEntry 4 }

arrisRouterFWDDNSExtendedPassword OBJECT-TYPE
    SYNTAX      DisplayString (SIZE (0..64))
    MAX-ACCESS  read-write
    STATUS      current
    DESCRIPTION  "Password to login to dynamic DNS service."
    ::= { arrisRouterFWDDNSExtendedEntry 5 }

arrisRouterFWDDNSExtendedIPAddrType OBJECT-TYPE
    SYNTAX      InetAddressType
    MAX-ACCESS  read-only
    STATUS      current
    DESCRIPTION  "Type for current DDNS IP address"
    ::= { arrisRouterFWDDNSExtendedEntry 6 }

arrisRouterFWDDNSExtendedIPAddr OBJECT-TYPE
    SYNTAX      InetAddress
    MAX-ACCESS  read-only
    STATUS      current
    DESCRIPTION  "Current DDNS IP address"
    ::= { arrisRouterFWDDNSExtendedEntry 7 }

arrisRouterFWDDNSExtendedStatus OBJECT-TYPE
    SYNTAX      DisplayString (SIZE (0..255))
    MAX-ACCESS  read-only
    STATUS      current
    DESCRIPTION  "String representing current status of DDNS service."
    ::= { arrisRouterFWDDNSExtendedEntry 8 }

arrisRouterFWDDNSExtendedRowStatus OBJECT-TYPE
     SYNTAX      RowStatus
     MAX-ACCESS  read-create
     STATUS      current
     DESCRIPTION "RowStatus used to add/remove rows from the table"
     ::= { arrisRouterFWDDNSExtendedEntry 9  }

arrisRouterFWDDNSExtendedHostnameTable OBJECT-TYPE
    SYNTAX      SEQUENCE OF ArrisRouterFWDDNSExtendedHostnameEntry
    MAX-ACCESS  not-accessible
    STATUS      current
    DESCRIPTION   "A table of dynamic DNS Hostname."
    ::= { arrisRouterFWDDNSExtended 2 }

arrisRouterFWDDNSExtendedHostnameEntry OBJECT-TYPE
      SYNTAX      ArrisRouterFWDDNSExtendedHostnameEntry
      MAX-ACCESS  not-accessible
      STATUS      current      DESCRIPTION "Table contains information for dynamic DNS settings"
      INDEX { arrisRouterFWDDNSExtednedHostnameDDNSIndex, arrisRouterFWDDNSExtednedHostnameIndex }
      ::= { arrisRouterFWDDNSExtendedHostnameTable 1 }

ArrisRouterFWDDNSExtendedHostnameEntry ::= SEQUENCE {
                arrisRouterFWDDNSExtednedHostnameIndex        Unsigned32,
                arrisRouterFWDDNSExtednedHostnameDDNSIndex    Unsigned32,
                arrisRouterFWDDNSExtendedHostnameValue        DisplayString,
                arrisRouterFWDDNSExtendedHostnameRowStatus    RowStatus
                }

arrisRouterFWDDNSExtednedHostnameIndex OBJECT-TYPE
    SYNTAX      Unsigned32
    MAX-ACCESS  not-accessible
    STATUS      current
    DESCRIPTION  "Index of this hostname."
    ::= { arrisRouterFWDDNSExtendedHostnameEntry 1 }

arrisRouterFWDDNSExtednedHostnameDDNSIndex OBJECT-TYPE
    SYNTAX      Unsigned32
    MAX-ACCESS  not-accessible
    STATUS      current
    DESCRIPTION  "Indicate this hostname is belong to which DDNS. This is used to mapping to arrisRouterFWDDNSExtendedIndex"
    ::= { arrisRouterFWDDNSExtendedHostnameEntry 2 }

arrisRouterFWDDNSExtendedHostnameValue OBJECT-TYPE
    SYNTAX      DisplayString (SIZE (0..255))
    MAX-ACCESS  read-write
    STATUS      current
    DESCRIPTION  "host name for dynamic DNS service."
    ::= { arrisRouterFWDDNSExtendedHostnameEntry 3 }

arrisRouterFWDDNSExtendedHostnameRowStatus OBJECT-TYPE
     SYNTAX      RowStatus
     MAX-ACCESS  read-create
     STATUS      current
     DESCRIPTION "RowStatus used to add/remove rows from the table"
     ::= { arrisRouterFWDDNSExtendedHostnameEntry 4 }

arrisRouterFWSrvTr69LastInstance OBJECT-TYPE
    SYNTAX      Unsigned32 (0..65535)
    MAX-ACCESS  read-write
    STATUS      current
    DESCRIPTION "A count indicates that how many instance TR-069 create."
    ::= { arrisRouterFWCfg 46 }

-- arrisRouterFWIPFilterExtend for LGI

arrisRouterFWIPFilterExtend                         OBJECT IDENTIFIER ::= { arrisRouterFWCfg 47 }

arrisRouterFWIPFilterExtTable  OBJECT-TYPE
    SYNTAX      SEQUENCE OF ArrisRouterFWIPFilterExtEntry
    MAX-ACCESS  not-accessible
    STATUS      current
    DESCRIPTION  "An extended table of IP and Port filtering rules. "
    ::= { arrisRouterFWIPFilterExtend 1 }

arrisRouterFWIPFilterExtEntry OBJECT-TYPE
    SYNTAX      ArrisRouterFWIPFilterExtEntry
    MAX-ACCESS  not-accessible
    STATUS      current
    DESCRIPTION  "An extended table of IP and Port filtering rules. "
    INDEX   { arrisRouterFWIPFilterExtIndex }
    ::= { arrisRouterFWIPFilterExtTable 1 }

ArrisRouterFWIPFilterExtEntry ::=
    SEQUENCE    {
                arrisRouterFWIPFilterExtIndex             Unsigned32,
                arrisRouterFWIPFilterExtIpVer             InetAddressType,
                arrisRouterFWIPFilterExtDirection        INTEGER,
                arrisRouterFWIPFilterExtProtoType      INTEGER,
                arrisRouterFWIPFilterExtSrcRange       INTEGER,
                arrisRouterFWIPFilterExtSrcStartAddr  InetAddress,
                arrisRouterFWIPFilterExtSrcEndAddr    InetAddress,
                arrisRouterFWIPFilterExtSrcPrefixLen   InetAddressPrefixLength,
                arrisRouterFWIPFilterExtDstRange       INTEGER,
                arrisRouterFWIPFilterExtDstStartAddr  InetAddress,
                arrisRouterFWIPFilterExtDstEndAddr    InetAddress,
                arrisRouterFWIPFilterExtDstPrefixLen   InetAddressPrefixLength,
                arrisRouterFWIPFilterExtSrcPortStart    Unsigned32,
                arrisRouterFWIPFilterExtSrcPortEnd      Unsigned32,
                arrisRouterFWIPFilterExtDstPortStart    Unsigned32,
                arrisRouterFWIPFilterExtDstPortEnd      Unsigned32,
                arrisRouterFWIPFilterExtAction             INTEGER,
                arrisRouterFWIPFilterExtRowStatus       RowStatus
                }

arrisRouterFWIPFilterExtIndex OBJECT-TYPE
    SYNTAX      Unsigned32 (1..64)
    MAX-ACCESS  not-accessible
    STATUS      current
    DESCRIPTION  "Indicates the instance of this table row. "
    ::= { arrisRouterFWIPFilterExtEntry 1 }

arrisRouterFWIPFilterExtIpVer OBJECT-TYPE
    SYNTAX      InetAddressType { ipv4(1), ipv6(2) }
    MAX-ACCESS  read-create
    STATUS      current
    DESCRIPTION  "Specifies IP protocol version. "
    ::= { arrisRouterFWIPFilterExtEntry 2 }

arrisRouterFWIPFilterExtDirection OBJECT-TYPE
    SYNTAX      INTEGER { inbound(0), outbound(1) }
    MAX-ACCESS  read-create
    STATUS      current
    DESCRIPTION "Determines IPv6 filtering rules to be applied to inbound or outbound packets. "
    ::= { arrisRouterFWIPFilterExtEntry 3 }

arrisRouterFWIPFilterExtProtoType OBJECT-TYPE
    SYNTAX      INTEGER { udp(0), tcp(1), udptcp(2), all(3), icmpv6(4), esp(5), ah(6), gre(7), ipv6encap(8), ipv4encap(9), ipv6fragment(10), l2tp(11) }
    MAX-ACCESS  read-create
    STATUS      current
    DESCRIPTION  "Specifies which protocol(s) are filtered. "
    ::= { arrisRouterFWIPFilterExtEntry 4 }

arrisRouterFWIPFilterExtSrcRange OBJECT-TYPE
    SYNTAX      INTEGER { range(0), all(1), single(2) }
    MAX-ACCESS  read-create
    STATUS      current
    DESCRIPTION  "Specifies the range of source IP address. "
    ::= { arrisRouterFWIPFilterExtEntry 5 }

arrisRouterFWIPFilterExtSrcStartAddr OBJECT-TYPE
    SYNTAX      InetAddress
    MAX-ACCESS  read-create
    STATUS      current
    DESCRIPTION  "Specifies the beginning of source IP range. "
    ::= { arrisRouterFWIPFilterExtEntry 6 }

arrisRouterFWIPFilterExtSrcEndAddr OBJECT-TYPE
    SYNTAX      InetAddress
    MAX-ACCESS  read-create
    STATUS      current
    DESCRIPTION  "Specifies the end of source IP range. "
    ::= { arrisRouterFWIPFilterExtEntry 7 }

arrisRouterFWIPFilterExtSrcPrefixLen OBJECT-TYPE
     SYNTAX      InetAddressPrefixLength
     MAX-ACCESS  read-create
     STATUS      current
     DESCRIPTION "Specifies the prefix for source IPv6 range. "
     ::= { arrisRouterFWIPFilterExtEntry 8 }

arrisRouterFWIPFilterExtDstRange OBJECT-TYPE
    SYNTAX      INTEGER { range(0), all(1), single(2) }
    MAX-ACCESS  read-create
    STATUS      current
    DESCRIPTION  "Specifies the range of destination IP address. "
    ::= { arrisRouterFWIPFilterExtEntry 9 }

arrisRouterFWIPFilterExtDstStartAddr OBJECT-TYPE
    SYNTAX      InetAddress
    MAX-ACCESS  read-create
    STATUS      current
    DESCRIPTION  "Specifies the beginning of destination IP range. "
    ::= { arrisRouterFWIPFilterExtEntry 10 }

arrisRouterFWIPFilterExtDstEndAddr OBJECT-TYPE
    SYNTAX      InetAddress
    MAX-ACCESS  read-create
    STATUS      current
    DESCRIPTION  "Specifies the end of destination IP range. "
    ::= { arrisRouterFWIPFilterExtEntry 11 }

arrisRouterFWIPFilterExtDstPrefixLen OBJECT-TYPE
     SYNTAX      InetAddressPrefixLength
     MAX-ACCESS  read-create
     STATUS      current
     DESCRIPTION "Specifies the prefix for destination IPv6 range. "
     ::= { arrisRouterFWIPFilterExtEntry 12 }

arrisRouterFWIPFilterExtSrcPortStart OBJECT-TYPE
    SYNTAX      Unsigned32 (0..65535)
    MAX-ACCESS  read-create
    STATUS      current
    DESCRIPTION  "Specifies the beginning of source port range. "
    ::= { arrisRouterFWIPFilterExtEntry 13 }

arrisRouterFWIPFilterExtSrcPortEnd OBJECT-TYPE
    SYNTAX      Unsigned32 (0..65535)
    MAX-ACCESS  read-create
    STATUS      current
    DESCRIPTION  "Specifies the end of source port range. "
    ::= { arrisRouterFWIPFilterExtEntry 14 }

arrisRouterFWIPFilterExtDstPortStart OBJECT-TYPE
    SYNTAX      Unsigned32 (0..65535)
    MAX-ACCESS  read-create
    STATUS      current
    DESCRIPTION  "Specifies the beginning of destination port range. "
    ::= { arrisRouterFWIPFilterExtEntry 15 }

arrisRouterFWIPFilterExtDstPortEnd OBJECT-TYPE
    SYNTAX      Unsigned32 (0..65535)
    MAX-ACCESS  read-create
    STATUS      current
    DESCRIPTION  "Specifies the end of destination port range. "
    ::= { arrisRouterFWIPFilterExtEntry 16 }

arrisRouterFWIPFilterExtAction OBJECT-TYPE
    SYNTAX      INTEGER { allow(0), deny(1) }
    MAX-ACCESS  read-create
    STATUS      current
    DESCRIPTION  "Does rule allow or deny access. "
    ::= { arrisRouterFWIPFilterExtEntry 17 }

arrisRouterFWIPFilterExtRowStatus OBJECT-TYPE
    SYNTAX      RowStatus
    MAX-ACCESS  read-create
    STATUS      current
    DESCRIPTION  "Row status to add/remove rows. "
    ::= { arrisRouterFWIPFilterExtEntry 18 }

arrisRouterFWIPFilterTodExtTable  OBJECT-TYPE
    SYNTAX      SEQUENCE OF ArrisRouterFWIPFilterTodExtEntry
    MAX-ACCESS  not-accessible
    STATUS      current
    DESCRIPTION  "An extended table of IP and Port filtering rules. "
    ::= { arrisRouterFWIPFilterExtend 2 }

arrisRouterFWIPFilterTodExtEntry OBJECT-TYPE
    SYNTAX      ArrisRouterFWIPFilterTodExtEntry
    MAX-ACCESS  not-accessible
    STATUS      current
    DESCRIPTION  "An extended table of IP and Port filtering rules. "
    INDEX   { arrisRouterFWIPFilterTodExtIndex }
    ::= { arrisRouterFWIPFilterTodExtTable 1 }

ArrisRouterFWIPFilterTodExtEntry ::=
    SEQUENCE    {
                arrisRouterFWIPFilterTodExtIndex             Unsigned32,
                arrisRouterFWIPFilterTodExtType               INTEGER,
                arrisRouterFWIPFilterTodExtSetting            Unsigned32
                }

arrisRouterFWIPFilterTodExtIndex OBJECT-TYPE
    SYNTAX      Unsigned32 (1..7)
    MAX-ACCESS  not-accessible
    STATUS      current
    DESCRIPTION  "Indicates the instance of this table row. "
    ::= { arrisRouterFWIPFilterTodExtEntry 1 }

arrisRouterFWIPFilterTodExtType OBJECT-TYPE
    SYNTAX      INTEGER { always(0), byhour(1), bydayhour(2) }
    MAX-ACCESS  read-write
    STATUS      current
    DESCRIPTION "Determines the type of todsetting "
    ::= { arrisRouterFWIPFilterTodExtEntry 2 }

arrisRouterFWIPFilterTodExtSetting OBJECT-TYPE
    SYNTAX      Unsigned32
    MAX-ACCESS  read-write
    STATUS      current
    DESCRIPTION "This is a 32-bit bitmask that sets the time of day to apply and days of the week to apply this rule.
 	Bits 0-6 correspond to Sunday-Saturday.  Set the bit high (1) to enable this rule for the day of the week.
 	Bits 7-30 apply to hours of the day 00:00:00-23:00:00.  Each it corresponds to an hour.  Set the bit high (1) to
 	enable the rule for specified hour. "
    ::= { arrisRouterFWIPFilterTodExtEntry 3 }

arrisRouterFWMACFilterTODExt  				OBJECT IDENTIFIER ::= { arrisRouterFWCfg 48 }

arrisRouterFWMACFilterTODExtType OBJECT-TYPE
    SYNTAX      INTEGER { always(0), byhour(1), bydayhour(2) }
    MAX-ACCESS  read-write
    STATUS      current
    DESCRIPTION  "Determines the type of todsetting "
    ::= { arrisRouterFWMACFilterTODExt 1}

arrisRouterFWMACFilterTODExtSetting OBJECT-TYPE
    SYNTAX      OCTET STRING (SIZE (22))
    MAX-ACCESS  read-write
    STATUS      current
    DESCRIPTION  "This is a 22byte bitmask that sets the days of week and time of day.
        22nd byte correspond to week days (Bits 0-6 -> Sunday-Saturday(bit 7 unused)). Set the bit high (1) to enable this rule for the day of the week.
        Rest of 21 bytes corresponds to hours of each day(24bits(for 24 hours) * 7 days = 168 bits).Set the bit high (1) to enable the rule for specified hour. Out of 24 bits for a day, 0th bit-> hour0-1,1st bit->hour1-2 and so on.
        When TOD type is 0(always), all 168bits are set to high by default.
        When TOD type is 1(byhour), 21st byte(bits 8-32) indicate hours enabled for the day(applies to all days of week).
        When TOD type is 2(bydayhour):
          Byte(19-21) -> hours of sunday
          Byte(16-18) -> hours of Monday
          Byte(13-15) -> hours of Tuesday
          Byte(10-12) -> hours of Wednesday
          Byte(7-9)   -> hours of Thursday
          Byte(4-6)   -> hours of Friday
          Byte(1-3)   -> hours of Saturday."
    ::= { arrisRouterFWMACFilterTODExt 2}

arrisRouterFWMACFilterAllowListRuleTr69LastInstance OBJECT-TYPE
    SYNTAX      Unsigned32
    MAX-ACCESS  read-write
    STATUS      current
    DESCRIPTION "A count indicates that how many instance TR-069 is created under Device.X_ARRIS_COM_Firewall.MACFilter.AllowList.Rule.{i}."
    ::= { arrisRouterFWCfg 49 }

arrisRouterFWMACFilterDenyListRuleTr69LastInstance OBJECT-TYPE
    SYNTAX      Unsigned32
    MAX-ACCESS  read-write
    STATUS      current
    DESCRIPTION "A count indicates that how many instance TR-069 is created under Device.X_ARRIS_COM_Firewall.MACFilter.DenyList.Rule.{i}."
    ::= { arrisRouterFWCfg 50 }

arrisRouterFWIPFilterRuleTr69LastInstance OBJECT-TYPE
    SYNTAX      Unsigned32
    MAX-ACCESS  read-write
    STATUS      current
    DESCRIPTION "A count indicates that how many instance TR-069 is created under Device.X_ARRIS_COM_Firewall.IPFilter.Rule.{i}."
    ::= { arrisRouterFWCfg 51 }

arrisRouterFWTr69PopulateEnabled OBJECT-TYPE
    SYNTAX      TruthValue
    MAX-ACCESS  read-write
    STATUS      current
    DESCRIPTION "Control whether TR-069 Device.Firewall.Chain.i. will be populated to ACS"
    DEFVAL      { false }
    ::= { arrisRouterFWCfg 52 }

arrisRouterUPnPRuleTable  OBJECT-TYPE
    SYNTAX      SEQUENCE OF ArrisRouterUPnPEntry
    MAX-ACCESS  not-accessible
    STATUS      current
    DESCRIPTION "Table contains information for UPnP PortForward Rules"
    ::= { arrisRouterFWCfg 53 }

arrisRouterUPnPRuleListEntry OBJECT-TYPE
      SYNTAX      ArrisRouterUPnPEntry
      MAX-ACCESS  not-accessible
      STATUS      current
      DESCRIPTION "Table contains information for UPnP Rules."
      INDEX   { arrisRouterUPnPRuleListIndex }
      ::= { arrisRouterUPnPRuleTable 1 }

ArrisRouterUPnPEntry ::= SEQUENCE {
                arrisRouterUPnPRuleListIndex             Unsigned32,
                arrisRouterUPnPProtoType             INTEGER,
                arrisRouterUPnPIPAddr             InetAddress,
                arrisRouterUPnPExternalport             Unsigned32,
                arrisRouterUPnPInternalport             Unsigned32
        }

arrisRouterUPnPRuleListIndex OBJECT-TYPE
    SYNTAX      Unsigned32
    MAX-ACCESS  not-accessible
    STATUS      current
    DESCRIPTION
        "Indicates the instance of this table row."
    ::= { arrisRouterUPnPRuleListEntry  1 }

arrisRouterUPnPProtoType OBJECT-TYPE
     SYNTAX      INTEGER { udp(0), tcp(1), both(2) }
     MAX-ACCESS  read-only
     STATUS      current
     DESCRIPTION "Prototype used by UPnP rule"

     ::= { arrisRouterUPnPRuleListEntry 2 }

arrisRouterUPnPIPAddr OBJECT-TYPE
     SYNTAX      InetAddress
     MAX-ACCESS  read-only
     STATUS      current
     DESCRIPTION "IP address on private network to forward to"
     ::= { arrisRouterUPnPRuleListEntry 3 }

arrisRouterUPnPExternalport OBJECT-TYPE
     SYNTAX      Unsigned32 (0..65535)
     MAX-ACCESS  read-only
     STATUS      current
     DESCRIPTION "External port to forward to"
     ::= { arrisRouterUPnPRuleListEntry 4 }

arrisRouterUPnPInternalport OBJECT-TYPE
     SYNTAX      Unsigned32 (0..65535)
     MAX-ACCESS  read-only
     STATUS      current
     DESCRIPTION "Internal port used"
     ::= { arrisRouterUPnPRuleListEntry 5 }

arrisRouterAdminPassword OBJECT-TYPE
    SYNTAX      DisplayString (SIZE (0..64))
    MAX-ACCESS  read-write
    STATUS      current
    DESCRIPTION "The administrative password to login to the router local device web UI."
    ::= { arrisRouterSysCfg 1 }

arrisRouterAdminTimeout OBJECT-TYPE
    SYNTAX      Unsigned32
    UNITS		"seconds"
    MAX-ACCESS  read-write
    STATUS      current
    DESCRIPTION "The administrative login timeout to the router local device web UI."
    DEFVAL { 600 }
    ::= { arrisRouterSysCfg 2 }

arrisRouterTimeZoneUTCOffset OBJECT-TYPE
    SYNTAX      Integer32
    MAX-ACCESS  read-write
    STATUS      current
    DESCRIPTION "The timezone setting, in seconds offset from UTC."
    ::= { arrisRouterSysCfg 3 }

arrisRouterReboot OBJECT-TYPE
    SYNTAX      INTEGER { restart(1) }
    MAX-ACCESS  read-write
    STATUS      current
    DESCRIPTION "This will restart the eRouter."
    ::= { arrisRouterSysCfg 4 }

arrisRouterDefaults OBJECT-TYPE
    SYNTAX      INTEGER { restoreUser(1), restoreGuest(2), restoreAll(3), restoreUserNoReboot(4), restoreGuestNoReboot(5), restoreAllNoReboot(6) }
    MAX-ACCESS  read-write
    STATUS      current
    DESCRIPTION "This will reset router settings to their defaults.
                To restore user settings for the primary network use restoreUser(1).
                To restore non-user 'guest' wireless settings use restoreGuest(2).
                To restore all settings on the device, use restoreAll(3)"
    ::= { arrisRouterSysCfg 5 }

arrisRouterLanguage OBJECT-TYPE
    SYNTAX      DisplayString (SIZE (0..32))
    MAX-ACCESS  read-write
    STATUS      current
    DESCRIPTION "Specify and retrieve the current language setting for the router."
    ::= { arrisRouterSysCfg 6 }

arrisRouterName OBJECT-TYPE
    SYNTAX      DisplayString (SIZE (0..64))
    MAX-ACCESS  read-write
    STATUS      current
    DESCRIPTION "Optional name for the router/gateway."
    ::= { arrisRouterSysCfg 7 }

arrisRouterSerialNumber OBJECT-TYPE
    SYNTAX      DisplayString (SIZE (0..32))
    MAX-ACCESS  read-only
    STATUS      current
    DESCRIPTION "Device serial number."
    ::= { arrisRouterSysCfg 8 }

arrisRouterBootCodeVersion OBJECT-TYPE
    SYNTAX      DisplayString (SIZE (0..32))
    MAX-ACCESS  read-only
    STATUS      current
    DESCRIPTION "Device boot code version."
    ::= { arrisRouterSysCfg 9 }

arrisRouterHardwareVersion OBJECT-TYPE
    SYNTAX      DisplayString (SIZE (0..32))
    MAX-ACCESS  read-only
    STATUS      current
    DESCRIPTION "Device hardware version."
    ::= { arrisRouterSysCfg 10 }

arrisRouterFirmwareVersion OBJECT-TYPE
    SYNTAX      DisplayString (SIZE (0..32))
    MAX-ACCESS  read-only
    STATUS      current
    DESCRIPTION "Device firmware version."
    ::= { arrisRouterSysCfg 11 }

arrisRouterLogLevel OBJECT-TYPE
    SYNTAX      INTEGER { noLogging(0), logError(1), logWarn(2), logInfo(3), logSuperInfo(4) }
    MAX-ACCESS  read-write
    STATUS      current
    DESCRIPTION "The logging level for the Arris SNMP daemon."
    DEFVAL { logError }
    ::= { arrisRouterSysCfg 12 }

arrisRouterCustomSettings OBJECT-TYPE
    SYNTAX      DisplayString
    MAX-ACCESS  read-write
    STATUS      current
    DESCRIPTION "A generic string used for web UI settings."
    ::= { arrisRouterSysCfg 13 }

arrisRouterCustomID OBJECT-TYPE
    SYNTAX      Integer32
    MAX-ACCESS  read-write
    STATUS      current
    DESCRIPTION "An integer which represents a customer ID for customization.
                 NOTE: This mib has read-only access property when Comcast uses TS9.x loads."
    ::= { arrisRouterSysCfg 14 }

arrisRouterCurrentTime OBJECT-TYPE
    SYNTAX      DateAndTime
    MAX-ACCESS  read-write
    STATUS      current
    DESCRIPTION "The current time on the router."
    ::= { arrisRouterSysCfg 15 }

arrisRouterAuthTable OBJECT-TYPE
      SYNTAX      SEQUENCE OF ArrisRouterAuthEntry
      MAX-ACCESS  not-accessible
      STATUS      current
      DESCRIPTION "Table contains information about web UI users, roles, and passwords."
      ::= { arrisRouterSysCfg 16 }

arrisRouterAuthEntry OBJECT-TYPE
      SYNTAX      ArrisRouterAuthEntry
      MAX-ACCESS  not-accessible
      STATUS      current
      DESCRIPTION "Table contains information about web UI users, roles, and passwords."
      INDEX { arrisRouterWanCurrentIPIndex }
      ::= { arrisRouterAuthTable 1 }

ArrisRouterAuthEntry ::= SEQUENCE {
        arrisRouterAuthIndex                    Unsigned32,
        arrisRouterAuthUserName                 DisplayString,
        arrisRouterAuthPassword                 DisplayString,
        arrisRouterAuthType                     DisplayString,
        arrisRouterAuthValidatePassword         DisplayString,
        arrisRouterAuthAccountEnabled           TruthValue,
        arrisRouterAuthDefaultAdminPassword     DisplayString
        }

arrisRouterAuthIndex OBJECT-TYPE
    SYNTAX      Unsigned32
    MAX-ACCESS  not-accessible
    STATUS      current
    DESCRIPTION "Indicates the instance of this table row."
    ::= { arrisRouterAuthEntry 1 }

arrisRouterAuthUserName OBJECT-TYPE
    SYNTAX      DisplayString (SIZE (0..32))
    MAX-ACCESS  read-create
    STATUS      current
    DESCRIPTION "The user name."
    ::= { arrisRouterAuthEntry 2 }

arrisRouterAuthPassword OBJECT-TYPE
    SYNTAX      DisplayString (SIZE (0..32))
    MAX-ACCESS  read-create
    STATUS      current
    DESCRIPTION "The password for the user."
    ::= { arrisRouterAuthEntry 3 }

arrisRouterAuthType OBJECT-TYPE
    SYNTAX      DisplayString (SIZE (0..32))
    MAX-ACCESS  read-create
    STATUS      current
    DESCRIPTION "A string describing the type of user, i.e. technician, admin, standard, etc.."
    ::= { arrisRouterAuthEntry 4 }

arrisRouterAuthValidatePassword OBJECT-TYPE
    SYNTAX      DisplayString (SIZE (0..32))
    MAX-ACCESS  read-create
    STATUS      current
    DESCRIPTION "Validation check on Web UI password for the user."
    ::= { arrisRouterAuthEntry 5 }

arrisRouterAuthAccountEnabled OBJECT-TYPE
    SYNTAX      TruthValue
    MAX-ACCESS  read-create
    STATUS      current
    DESCRIPTION "Get/set whether this account is disabled or enabled."
    ::= { arrisRouterAuthEntry 6 }

arrisRouterAuthDefaultAdminPassword OBJECT-TYPE
    SYNTAX      DisplayString (SIZE (0..32))
    MAX-ACCESS  read-only
    STATUS      current
    DESCRIPTION "Default Admin password set by the factory."
    ::= { arrisRouterAuthEntry 7 }

arrisRouterSNTPSettings			OBJECT IDENTIFIER ::= { arrisRouterSysCfg 17 }

arrisRouterEnableSNTP OBJECT-TYPE
    SYNTAX      INTEGER { disable(0), enable(1) }
    MAX-ACCESS  read-write
    STATUS      current
    DESCRIPTION "Enable/disable the SNTP service."
    ::= { arrisRouterSNTPSettings 1 }

arrisRouterApplySNTPSettings OBJECT-TYPE
    SYNTAX      INTEGER { noOp(0), applySettings(1) }
    MAX-ACCESS  read-write
    STATUS      current
    DESCRIPTION "Set the NTP settings."
    ::= { arrisRouterSNTPSettings 2 }

arrisRouterSNTPTableFreeIdx OBJECT-TYPE
    SYNTAX      Integer32
    MAX-ACCESS  read-only
    STATUS      current
    DESCRIPTION "The lowest available index to that may be used to add a row instance to the arrisRouterSNTPServerTable."
    ::= { arrisRouterSNTPSettings 3 }

arrisRouterSNTPServerTable OBJECT-TYPE
    SYNTAX      SEQUENCE OF ArrisRouterSNTPServerEntry
    MAX-ACCESS  not-accessible
    STATUS      current
    DESCRIPTION  "A table of SNTP servers."
    ::= { arrisRouterSNTPSettings 4 }

arrisRouterSNTPServerEntry OBJECT-TYPE
    SYNTAX      ArrisRouterSNTPServerEntry
    MAX-ACCESS  not-accessible
    STATUS      current
    DESCRIPTION  "A table of SNTP servers."
    INDEX   { arrisRouterSNTPServerIndex }
    ::= { arrisRouterSNTPServerTable 1 }

ArrisRouterSNTPServerEntry ::=
    SEQUENCE    {
                arrisRouterSNTPServerIndex		Integer32,
                arrisRouterSNTPServerAddrType		InetAddressType,
                arrisRouterSNTPServerAddr		InetAddress,
                arrisRouterSNTPServerName		DisplayString,
                arrisRouterSNTPServerStatus		RowStatus
                }

arrisRouterSNTPServerIndex OBJECT-TYPE
    SYNTAX      Integer32 (1..3)
    MAX-ACCESS  not-accessible
    STATUS      current
    DESCRIPTION "Indicates the instance of this table row."
    ::= { arrisRouterSNTPServerEntry 1 }

arrisRouterSNTPServerAddrType OBJECT-TYPE
    SYNTAX      InetAddressType
    MAX-ACCESS  read-create
    STATUS      current
    DESCRIPTION "IP address type of Network Time Server."
    ::= { arrisRouterSNTPServerEntry 2 }

arrisRouterSNTPServerAddr OBJECT-TYPE
    SYNTAX      InetAddress
    MAX-ACCESS  read-create
    STATUS      current
    DESCRIPTION "IP address of Network Time Server."
    ::= { arrisRouterSNTPServerEntry 3 }

arrisRouterSNTPServerName OBJECT-TYPE
    SYNTAX      DisplayString (SIZE(0..64))
    MAX-ACCESS  read-create
    STATUS      current
    DESCRIPTION "Host name of Network Time Server.
                 NOTE: For TS7.x, this mib has no value length limitation."
    ::= { arrisRouterSNTPServerEntry 4 }

arrisRouterSNTPServerStatus OBJECT-TYPE
    SYNTAX      RowStatus
    MAX-ACCESS  read-create
    STATUS      current
    DESCRIPTION
        "The status of this conceptual row.

         To create a row in this table, a manager must set this object to
         either createAndGo(4) or createAndWait(5).

         Until instances of all corresponding columns are appropriately
         configured, the value of the corresponding instance of the
         arrisRouterSNTPServerStatus column is 'notReady'.

         Only rows with a status of active(1) will be applied."
    ::= { arrisRouterSNTPServerEntry 5 }


arrisRouterEmailSettings			OBJECT IDENTIFIER ::= { arrisRouterSysCfg 18 }

arrisRouterEmailServerName OBJECT-TYPE
    SYNTAX      DisplayString
    MAX-ACCESS  read-write
    STATUS      current
    DESCRIPTION "Name of email server to use."
    ::= { arrisRouterEmailSettings 1 }

arrisRouterEmailServerUser OBJECT-TYPE
    SYNTAX      DisplayString
    MAX-ACCESS  read-write
    STATUS      current
    DESCRIPTION "User name used to login to SMTP email server (optional)."
    ::= { arrisRouterEmailSettings 2 }

arrisRouterEmailServerPW OBJECT-TYPE
    SYNTAX      DisplayString
    MAX-ACCESS  read-write
    STATUS      current
    DESCRIPTION "Password used to login to SMTP email server (optional)."
    ::= { arrisRouterEmailSettings 3 }

arrisRouterEmailAddress OBJECT-TYPE
    SYNTAX      DisplayString
    MAX-ACCESS  read-write
    STATUS      current
    DESCRIPTION "Email address to send to."
    ::= { arrisRouterEmailSettings 4 }

arrisRouterEnableLogEmail OBJECT-TYPE
    SYNTAX      TruthValue	 -- make an integer bitmask for log types
    MAX-ACCESS  read-write
    STATUS      current
    DESCRIPTION "Specify whether or not logs are sent via email."
    DEFVAL { false }
    ::= { arrisRouterEmailSettings 5 }

arrisRouterEmailApplySettings OBJECT-TYPE
    SYNTAX      INTEGER { applySettings(1) }
    MAX-ACCESS  read-write
    STATUS      current
    DESCRIPTION "Apply the email settings."
    ::= { arrisRouterEmailSettings 6 }

arrisRouterEmailNotifyTypes                         OBJECT IDENTIFIER ::= { arrisRouterEmailSettings 7 }

-- START arrisRouterEmailNotifyTypes
arrisRouterEmailNotifyTypeFW OBJECT-TYPE
    SYNTAX      TruthValue
    MAX-ACCESS  read-write
    STATUS      current
    DESCRIPTION "Specify whether or not FireWall logs are send via email"
    DEFVAL { false }
    ::= { arrisRouterEmailNotifyTypes 1 }

arrisRouterEmailNotifyTypePC OBJECT-TYPE
    SYNTAX      TruthValue
    MAX-ACCESS  read-write
    STATUS      current
    DESCRIPTION "Specify whether or not Parental Control logs are send via email"
    DEFVAL { false }
    ::= { arrisRouterEmailNotifyTypes 2 }

arrisRouterEmailNotifyTypeAlert OBJECT-TYPE
    SYNTAX      TruthValue
    MAX-ACCESS  read-write
    STATUS      current
    DESCRIPTION "Specify whether or not Alert logs are send via email"
    DEFVAL { false }
    ::= { arrisRouterEmailNotifyTypes 3 }

arrisRouterEmailNotifyTypeWarning OBJECT-TYPE
    SYNTAX      TruthValue
    MAX-ACCESS  read-write
    STATUS      current
    DESCRIPTION "Specify whether or not Warning logs are send via email"
    DEFVAL { false }
    ::= { arrisRouterEmailNotifyTypes 4 }
-- END arrisRouterEmailNotifyTypes

arrisRouterEmailSenderAddress OBJECT-TYPE
    SYNTAX      DisplayString
    MAX-ACCESS  read-write
    STATUS      current
    DESCRIPTION "Email address of sender"
    ::= { arrisRouterEmailSettings 8 }

arrisRouterEmailSend OBJECT-TYPE
    SYNTAX      INTEGER { none(0), networkCredential(1), modemCredential(2) }
    MAX-ACCESS  read-write
    STATUS      current
    DESCRIPTION "Sends email. Walk of this MIB always returns none(0). "
    ::= { arrisRouterEmailSettings 9 }

-- Setting for Parent control log
arrisRouterLogSettings			OBJECT IDENTIFIER ::= { arrisRouterSysCfg 19 }

arrisRouterUserLogs			OBJECT IDENTIFIER ::= { arrisRouterLogSettings 1 }

arrisRouterFirewallLogTable OBJECT-TYPE
    SYNTAX      SEQUENCE OF ArrisRouterFirewallLogEntry
    MAX-ACCESS  not-accessible
    STATUS      current
	DESCRIPTION  "A table of where each row represents an entry in the firewall log."
	::= { arrisRouterUserLogs 1 }

arrisRouterFirewallLogEntry OBJECT-TYPE
    SYNTAX      ArrisRouterFirewallLogEntry
    MAX-ACCESS  not-accessible
    STATUS      current
	DESCRIPTION  "A table of where each row represents an entry in the firewall log."
    INDEX   { arrisRouterFWLogIndex }
    ::= { arrisRouterFirewallLogTable 1 }

ArrisRouterFirewallLogEntry ::=
    SEQUENCE    {
                arrisRouterFWLogIndex					Integer32,
                arrisRouterFWLogTime					DateAndTime,
                arrisRouterFWLogInfo					DisplayString
                }

arrisRouterFWLogIndex OBJECT-TYPE
    SYNTAX      Integer32 (1..30)
    MAX-ACCESS  not-accessible
    STATUS      current
    DESCRIPTION "Indicates the instance of this table row."
    ::= { arrisRouterFirewallLogEntry 1 }

arrisRouterFWLogTime OBJECT-TYPE
    SYNTAX      DateAndTime
    MAX-ACCESS  read-only
    STATUS      current
    DESCRIPTION "Date and time when this event occurred."
    ::= { arrisRouterFirewallLogEntry 2 }

arrisRouterFWLogInfo OBJECT-TYPE
    SYNTAX      DisplayString
    MAX-ACCESS  read-only
    STATUS      current
    DESCRIPTION "Event/log entry."
    ::= { arrisRouterFirewallLogEntry 3 }


arrisRouterParentalContLogTable OBJECT-TYPE
    SYNTAX      SEQUENCE OF ArrisRouterParentalContLogEntry
    MAX-ACCESS  not-accessible
    STATUS      current
	DESCRIPTION  "A table of where each row represents an entry in the parental control log."
	::= { arrisRouterUserLogs 2 }

arrisRouterParentalContLogEntry OBJECT-TYPE
    SYNTAX      ArrisRouterParentalContLogEntry
    MAX-ACCESS  not-accessible
    STATUS      current
	DESCRIPTION  "A table of where each row represents an entry in the parental control log."
    INDEX   { arrisRouterPCLogIndex }
    ::= { arrisRouterParentalContLogTable 1 }

ArrisRouterParentalContLogEntry ::=
    SEQUENCE    {
                arrisRouterPCLogIndex					Integer32,
                arrisRouterPCLogTime					DateAndTime,
                arrisRouterPCLogInfo					DisplayString,
                arrisRouterPCLogType					Integer32
                }

arrisRouterPCLogIndex OBJECT-TYPE
    SYNTAX      Integer32 (1..30)
    MAX-ACCESS  not-accessible
    STATUS      current
    DESCRIPTION "Indicates the instance of this table row."
    ::= { arrisRouterParentalContLogEntry 1 }

arrisRouterPCLogTime OBJECT-TYPE
    SYNTAX      DateAndTime
    MAX-ACCESS  read-only
    STATUS      current
    DESCRIPTION "Date and time when this event occurred."
    ::= { arrisRouterParentalContLogEntry 2 }

arrisRouterPCLogInfo OBJECT-TYPE
    SYNTAX      DisplayString
    MAX-ACCESS  read-only
    STATUS      current
    DESCRIPTION "Event/log entry."
    ::= { arrisRouterParentalContLogEntry 3 }

arrisRouterPCLogType OBJECT-TYPE
    SYNTAX      Integer32 (0..3)
    MAX-ACCESS  read-create
    STATUS      current
    DESCRIPTION "Indicates the type of log."
    ::= { arrisRouterParentalContLogEntry 4 }

arrisRouterChangeLogTable OBJECT-TYPE
    SYNTAX      SEQUENCE OF ArrisRouterChangeLogEntry
    MAX-ACCESS  not-accessible
    STATUS      current
    DESCRIPTION  "A table of where each row represents an entry in the user change log.  This is a log of configuration changes by the user."
    ::= { arrisRouterUserLogs 3 }

arrisRouterChangeLogEntry OBJECT-TYPE
    SYNTAX      ArrisRouterChangeLogEntry
    MAX-ACCESS  not-accessible
    STATUS      current
    DESCRIPTION  "A table of where each row represents an entry in the user change log.  This is a log of configuration changes by the user."
    INDEX   { arrisRouterChangeLogIndex }
    ::= { arrisRouterChangeLogTable 1 }

ArrisRouterChangeLogEntry ::=
    SEQUENCE    {
                arrisRouterChangeLogIndex					Integer32,
                arrisRouterChangeLogTime					DateAndTime,
                arrisRouterChangeLogInfo					DisplayString
                }

arrisRouterChangeLogIndex OBJECT-TYPE
    SYNTAX      Integer32 (1..40)
    MAX-ACCESS  not-accessible
    STATUS      current
    DESCRIPTION "Indicates the instance of this table row."
    ::= { arrisRouterChangeLogEntry 1 }

arrisRouterChangeLogTime OBJECT-TYPE
    SYNTAX      DateAndTime
    MAX-ACCESS  read-only
    STATUS      current
    DESCRIPTION "Date and time when this event occurred."
    ::= { arrisRouterChangeLogEntry 2 }

arrisRouterChangeLogInfo OBJECT-TYPE
    SYNTAX      DisplayString
    MAX-ACCESS  read-only
    STATUS      current
    DESCRIPTION "Event/log entry."
    ::= { arrisRouterChangeLogEntry 3 }

arrisRouterDebugLogTable OBJECT-TYPE
    SYNTAX      SEQUENCE OF ArrisRouterDebugLogEntry
    MAX-ACCESS  not-accessible
    STATUS      current
    DESCRIPTION  "A table of where each row represents a debug log item."
    ::= { arrisRouterUserLogs 4 }

arrisRouterDebugLogEntry OBJECT-TYPE
    SYNTAX      ArrisRouterDebugLogEntry
    MAX-ACCESS  not-accessible
    STATUS      current
    DESCRIPTION  "A table of where each row represents a debug log item."
    INDEX   { arrisRouterDebugLogIndex }
    ::= { arrisRouterDebugLogTable 1 }

ArrisRouterDebugLogEntry ::=
    SEQUENCE    {
                arrisRouterDebugLogIndex				Integer32,
                arrisRouterDebugLogTime					DateAndTime,
                arrisRouterDebugLogInfo					DisplayString
                }

arrisRouterDebugLogIndex OBJECT-TYPE
    SYNTAX      Integer32 (1..100)
    MAX-ACCESS  not-accessible
    STATUS      current
    DESCRIPTION "Indicates the instance of this table row."
    ::= { arrisRouterDebugLogEntry 1 }

arrisRouterDebugLogTime OBJECT-TYPE
    SYNTAX      DateAndTime
    MAX-ACCESS  read-only
    STATUS      current
    DESCRIPTION "Date and time when this event occurred."
    ::= { arrisRouterDebugLogEntry 2 }

arrisRouterDebugLogInfo OBJECT-TYPE
    SYNTAX      DisplayString
    MAX-ACCESS  read-only
    STATUS      current
    DESCRIPTION "Event/log entry."
    ::= { arrisRouterDebugLogEntry 3 }

arrisRouterDHCPLogTable OBJECT-TYPE
    SYNTAX      SEQUENCE OF ArrisRouterDHCPLogEntry
    MAX-ACCESS  not-accessible
    STATUS      current
    DESCRIPTION  "A table of where each row represents a debug log item."
    ::= { arrisRouterUserLogs 5 }

arrisRouterDHCPLogEntry OBJECT-TYPE
    SYNTAX      ArrisRouterDHCPLogEntry
    MAX-ACCESS  not-accessible
    STATUS      current
    DESCRIPTION  "A table of where each row represents a debug log item."
    INDEX   { arrisRouterDHCPLogIndex }
    ::= { arrisRouterDHCPLogTable 1 }

ArrisRouterDHCPLogEntry ::=
    SEQUENCE    {
                arrisRouterDHCPLogIndex				Integer32,
                arrisRouterDHCPLogTime				DateAndTime,
                arrisRouterDHCPLogInfo				DisplayString
                }

arrisRouterDHCPLogIndex OBJECT-TYPE
    SYNTAX      Integer32 (1..100)
    MAX-ACCESS  not-accessible
    STATUS      current
    DESCRIPTION "Indicates the instance of this table row."
    ::= { arrisRouterDHCPLogEntry 1 }

arrisRouterDHCPLogTime OBJECT-TYPE
    SYNTAX      DateAndTime
    MAX-ACCESS  read-only
    STATUS      current
    DESCRIPTION "Date and time when this event occurred."
    ::= { arrisRouterDHCPLogEntry 2 }

arrisRouterDHCPLogInfo OBJECT-TYPE
    SYNTAX      DisplayString
    MAX-ACCESS  read-only
    STATUS      current
    DESCRIPTION "Event/log entry."
    ::= { arrisRouterDHCPLogEntry 3 }

arrisRouterLanClientLogTable OBJECT-TYPE
    SYNTAX      SEQUENCE OF ArrisRouterLanClientLogEntry
    MAX-ACCESS  not-accessible
    STATUS      current
    DESCRIPTION  "A table where each row represents a log item pertaining to LAN client events."
    ::= { arrisRouterUserLogs 6 }

arrisRouterLanClientLogEntry OBJECT-TYPE
    SYNTAX      ArrisRouterLanClientLogEntry
    MAX-ACCESS  not-accessible
    STATUS      current
    DESCRIPTION  "An entry in arrisRouterLanClientLogTable."
    INDEX   { arrisRouterLanClientLogIndex }
    ::= { arrisRouterLanClientLogTable 1 }

ArrisRouterLanClientLogEntry ::=
    SEQUENCE    {
                arrisRouterLanClientLogIndex				Integer32,
                arrisRouterLanClientLogTime				DateAndTime,
                arrisRouterLanClientLogInfo				DisplayString
                }

arrisRouterLanClientLogIndex OBJECT-TYPE
    SYNTAX      Integer32 (1..100)
    MAX-ACCESS  not-accessible
    STATUS      current
    DESCRIPTION "Indicates the instance of this table row."
    ::= { arrisRouterLanClientLogEntry 1 }

arrisRouterLanClientLogTime OBJECT-TYPE
    SYNTAX      DateAndTime
    MAX-ACCESS  read-only
    STATUS      current
    DESCRIPTION "Date and time when this event occurred."
    ::= { arrisRouterLanClientLogEntry 2 }

arrisRouterLanClientLogInfo OBJECT-TYPE
    SYNTAX      DisplayString
    MAX-ACCESS  read-only
    STATUS      current
    DESCRIPTION "Event/log entry."
    ::= { arrisRouterLanClientLogEntry 3 }

arrisRouterFirewallLogExtTable OBJECT-TYPE
    SYNTAX      SEQUENCE OF ArrisRouterFirewallLogExtEntry
    MAX-ACCESS  not-accessible
    STATUS      current
    DESCRIPTION  "An extended firewall log entry, it is only used for LGI at present."
    ::= { arrisRouterUserLogs 7 }

arrisRouterFirewallLogExtEntry OBJECT-TYPE
    SYNTAX      ArrisRouterFirewallLogExtEntry
    MAX-ACCESS  not-accessible
    STATUS      current
    DESCRIPTION  "An extended firewall log entry, it is only used for LGI at present."
    INDEX   { arrisRouterFWLogExtIndex }
    ::= { arrisRouterFirewallLogExtTable 1 }

ArrisRouterFirewallLogExtEntry ::=
    SEQUENCE    {
                arrisRouterFWLogExtIndex            Integer32,
                arrisRouterFWLogLatestEventTime     DateAndTime,
                arrisRouterFWLogLatestEventInfo     DisplayString,
                arrisRouterFWLogEventCount          Integer32
                }

arrisRouterFWLogExtIndex OBJECT-TYPE
    SYNTAX      Integer32 (1..5)
    MAX-ACCESS  not-accessible
    STATUS      current
    DESCRIPTION "Indicates firewall log event type. It is only used for LGI at present.
                    1.TCP Port Scan
                    2.UDP Port Scan
                    3.SYN Flood
                    4.UDP Flood
                    5.ICMP Flood"
    ::= { arrisRouterFirewallLogExtEntry 1 }

arrisRouterFWLogLatestEventTime OBJECT-TYPE
    SYNTAX      DateAndTime
    MAX-ACCESS  read-only
    STATUS      current
    DESCRIPTION "Date and time of the latest event for each event type. It is only used for LGI at present."
    ::= { arrisRouterFirewallLogExtEntry 2 }

arrisRouterFWLogLatestEventInfo OBJECT-TYPE
    SYNTAX      DisplayString
    MAX-ACCESS  read-only
    STATUS      current
    DESCRIPTION "Event log entry of the latest event for each event type. It is only used for LGI at present."
    ::= { arrisRouterFirewallLogExtEntry 3 }

arrisRouterFWLogEventCount OBJECT-TYPE
    SYNTAX      Integer32
    MAX-ACCESS  read-only
    STATUS      current
    DESCRIPTION "Indicates counter of the latest event for each event type. It is only used for LGI at present."
    ::= { arrisRouterFirewallLogExtEntry 4 }

arrisRouterMocaLogTable OBJECT-TYPE
    SYNTAX      SEQUENCE OF ArrisRouterMocaLogEntry
    MAX-ACCESS  not-accessible
    STATUS      current
    DESCRIPTION  "A table of where each row represents a Moca log item."
    ::= { arrisRouterUserLogs 9 }

arrisRouterMocaLogEntry OBJECT-TYPE
    SYNTAX      ArrisRouterMocaLogEntry
    MAX-ACCESS  not-accessible
    STATUS      current
	DESCRIPTION  "A table of where each row represents a Moca log item."
    INDEX   { arrisRouterMocaLogIndex }
    ::= { arrisRouterMocaLogTable 1 }

ArrisRouterMocaLogEntry ::=
    SEQUENCE    {
                arrisRouterMocaLogIndex					Integer32,
                arrisRouterMocaLogTime					DateAndTime,
                arrisRouterMocaLogInfo					DisplayString
                }

arrisRouterMocaLogIndex OBJECT-TYPE
    SYNTAX      Integer32 (1..100)
    MAX-ACCESS  not-accessible
    STATUS      current
    DESCRIPTION "Indicates the instance of this table row."
    ::= { arrisRouterMocaLogEntry 1 }

arrisRouterMocaLogTime OBJECT-TYPE
    SYNTAX      DateAndTime
    MAX-ACCESS  read-only
    STATUS      current
    DESCRIPTION "Date and time when this event occurred."
    ::= { arrisRouterMocaLogEntry 2 }

arrisRouterMocaLogInfo OBJECT-TYPE
    SYNTAX      DisplayString
    MAX-ACCESS  read-only
    STATUS      current
    DESCRIPTION "Event/log entry"
    ::= { arrisRouterMocaLogEntry 3 }

arrisRouterMSOLogs			OBJECT IDENTIFIER ::= { arrisRouterLogSettings 2 }

arrisRouterMSOChgLogTable OBJECT-TYPE
    SYNTAX      SEQUENCE OF ArrisRouterMSOChgLogEntry
    MAX-ACCESS  not-accessible
    STATUS      current
    DESCRIPTION  "A table of where each row represents an entry in the MSO change log.  This is a log of configuration changes that are not done by the user.
                Assumed to be the MSO remotely or a technician."
    ::= { arrisRouterMSOLogs 1 }

arrisRouterMSOChgLogEntry OBJECT-TYPE
    SYNTAX      ArrisRouterMSOChgLogEntry
    MAX-ACCESS  not-accessible
    STATUS      current
    DESCRIPTION  "A table of where each row represents an entry in the MSO change log.  This is a log of configuration changes that are not done by the user.
                Assumed to be the MSO remotely or a technician."
    INDEX   { arrisRouterMSOChgLogIndex }
    ::= { arrisRouterMSOChgLogTable 1 }

ArrisRouterMSOChgLogEntry ::=
    SEQUENCE    {
                arrisRouterMSOChgLogIndex					Integer32,
                arrisRouterMSOChgLogTime					DateAndTime,
                arrisRouterMSOChgLogInfo					DisplayString
                }

arrisRouterMSOChgLogIndex OBJECT-TYPE
    SYNTAX      Integer32 (1..40)
    MAX-ACCESS  not-accessible
    STATUS      current
    DESCRIPTION "Indicates the instance of this table row."
    ::= { arrisRouterMSOChgLogEntry 1 }

arrisRouterMSOChgLogTime OBJECT-TYPE
    SYNTAX      DateAndTime
    MAX-ACCESS  read-only
    STATUS      current
    DESCRIPTION "Date and time when this event occurred."
    ::= { arrisRouterMSOChgLogEntry 2 }

arrisRouterMSOChgLogInfo OBJECT-TYPE
    SYNTAX      DisplayString
    MAX-ACCESS  read-only
    STATUS      current
    DESCRIPTION "Event/log entry."
    ::= { arrisRouterMSOChgLogEntry 3 }

arrisRouterClearMSOLogs OBJECT-TYPE
    SYNTAX      INTEGER { noOp(0), clearLogs(1) }
    MAX-ACCESS  read-write
    STATUS      current
    DESCRIPTION "Clear user logs."
    ::= { arrisRouterMSOLogs 2 }

arrisRouterClearLogs OBJECT-TYPE
    SYNTAX      INTEGER { noOp(0), clearUserLogs(1), clearMSOLogs(2), clearAllLogs(3) }
    MAX-ACCESS  read-write
    STATUS      current
    DESCRIPTION "Clear logs."
    ::= { arrisRouterLogSettings 3 }

arrisRouterChangeLogFilter OBJECT-TYPE
    SYNTAX      INTEGER { showAllLogs(0), hideTechnicianSettings (1) }
    MAX-ACCESS  read-write
    STATUS      current
    DESCRIPTION "Set this OID to hideTechnicianSettings before walking arrisRouterChangeLogTable to hide any settings made by a technician.
                This is primarily for the Web GUI so that any 'technician-only' settings made are not displayed to the consumer."
    DEFVAL { hideTechnicianSettings }
    ::= { arrisRouterLogSettings 4 }

arrisRouterDumpDocsisLog OBJECT-TYPE
    SYNTAX      INTEGER { dumpLogs (1) }
    MAX-ACCESS  read-write
    STATUS      current
    DESCRIPTION "Set this OID to 'dumpLogs to dump a detailed log of the DOCSIS/CM configuration file to the Arris Gateway logfile."
    ::= { arrisRouterLogSettings 5 }

arrisRouterTACACSAddr OBJECT-TYPE
    SYNTAX      DisplayString (SIZE(0..255))
    MAX-ACCESS  read-write
    STATUS      current
    DESCRIPTION "The FQDN or IP Address of the Server."
    ::= { arrisRouterSysCfg 20 }

arrisRouterTACACSPort OBJECT-TYPE
    SYNTAX      Integer32
    MAX-ACCESS  read-write
    STATUS      current
    DESCRIPTION "The Server port."
	DEFVAL { 49 }
    ::= { arrisRouterSysCfg 21 }

arrisRouterTACACSSecretKey OBJECT-TYPE
    SYNTAX      DisplayString (SIZE(0..32))
    MAX-ACCESS  read-write
    STATUS      current
    DESCRIPTION "The secret key used to communicate with the Server."
    ::= { arrisRouterSysCfg 22 }

arrisRouterXmlProvisioningFile OBJECT-TYPE
    SYNTAX      DisplayString (SIZE(0..255))
    MAX-ACCESS  read-write
    STATUS      current
    DESCRIPTION "The fully qualified path to a provisioning file to load.  The file may be an URL using HTTP or TFTP.
                  This value is not permanently stored in non-volatile memory and is cleared on reboot."
    ::= { arrisRouterSysCfg 23 }

arrisRouterXmlProvisioningStatus  OBJECT-TYPE
    SYNTAX INTEGER {
                notSpecified(1),
                inProgress(2),
                downloadSuccess(3),
                serverError(4),
                fileNotFound(5),
                fileFormatError(6),
                downloadFromMgt(7)
                }
    MAX-ACCESS  read-write
    STATUS      current
    DESCRIPTION "This object shows the download status of the Gateway XML
            configuration file. It can also be used to initiate an on demand
            download of the XML configuration file by setting the value to
            downloadFromMgt (7). This value is not permanently stored in
            non-volatile memory and shall reset to notSpecified (1) upon reboot."
    DEFVAL { notSpecified }
    ::= { arrisRouterSysCfg 24 }

arrisRouterBlockNonArrisDevices OBJECT-TYPE
     SYNTAX      INTEGER { blockAllInterfaces(1), noBlocking(2), blockMocaOnly(3) }
     MAX-ACCESS  read-write
     STATUS      current
     DESCRIPTION "If blocking is enabled only Arris devices can connect to the LAN.  This can only be set via the WAN interface or the CM configuration file.  This can not be set via from the LAN."
     DEFVAL { noBlocking }
    ::= { arrisRouterSysCfg 26 }

arrisRouterDHCPLogLevel OBJECT-TYPE
    SYNTAX      INTEGER { noLogging(0), logError(1), logWarn(2), logInfo(3) }
    MAX-ACCESS  read-write
    STATUS      current
    DESCRIPTION "The logging level for DHCP related messages for eRouter."
	DEFVAL { logError }
    ::= { arrisRouterSysCfg 27 }

arrisRouterTechnicianName OBJECT-TYPE
    SYNTAX      DisplayString
    MAX-ACCESS  read-write
    STATUS      current
    DESCRIPTION "The technician user name."
    ::= { arrisRouterSysCfg 28 }

arrisRouterEnableLanEtherPrivateWanBlock OBJECT-TYPE
    SYNTAX      TruthValue
    MAX-ACCESS  read-write
    STATUS      current
    DESCRIPTION "Set to true to disable transmit/receive between Ethernet LAN ports and the 'private WAN' interface on the Media Gateway.  "
    DEFVAL { false }
    ::= { arrisRouterSysCfg 29 }

arrisRouterTACACSIPAddrType OBJECT-TYPE
    SYNTAX      InetAddressType
    MAX-ACCESS  read-write
    STATUS      current
    DESCRIPTION "The FQDN or IP Address of the Server."
    ::= { arrisRouterSysCfg 30 }

arrisRouterTACACSIPAddr OBJECT-TYPE
    SYNTAX      InetAddress
    MAX-ACCESS  read-write
    STATUS      current
    DESCRIPTION "The FQDN or IP Address of the Server."
    ::= { arrisRouterSysCfg 31 }

arrisRouterEnabledInterfaces OBJECT-TYPE
    SYNTAX      Integer32
    MAX-ACCESS  read-write
    STATUS      current
    DESCRIPTION "An integer representing a bitmask that specifies which interfaces are enabled.  Changing this value will cause an immedidate reboot of the device to affect the change.
                 0x00001  -- DOCSIS CM HAL
                 0x00002  -- Ethernet HAL
                 0x00004  -- HPNA HAL
                 0x00008  -- USB HAL
                 0x00010  -- IP Stack 1 HAL
                 0x00020  -- IP Stack 2 HAL
                 0x00040  -- IP Stack 3 HAL
                 0x00080  -- IP Stack 4 HAL
                 0x00100  -- Davic HAL
                 0x00200  -- PCI HAL
                 0x00400  -- Bluetooth HAL
                 0x00800  -- 802.11 HAL
                 0x01000  -- PacketGenerator HAL
                 0x02000  -- IP Stack 5 HAL
                 0x04000  -- IP Stack 6 HAL
                 0x08000  -- IP Stack 7 HAL
                 0x10000  -- IP Stack 8 HAL
                 0x20000  -- WAN Ethernet HAL
                 0x40000  -- SCB HAL
                 0x80000  -- MOCA HAL.
                 Currently the only valid bitmasks are: 657651 (0xA08F3) and 657523 (0xA0873) on the Media Gateway."
    ::= { arrisRouterSysCfg 32 }


arrisRouterEnabledInterfacesString OBJECT-TYPE
    SYNTAX      DisplayString
    MAX-ACCESS  read-only
    STATUS      current
    DESCRIPTION "An string which describes the enabled interfaces."
    ::= { arrisRouterSysCfg 33 }

arrisRouterInboundTrafficLogEnable OBJECT-TYPE
    SYNTAX      TruthValue
    MAX-ACCESS  read-write
    STATUS      current
    DESCRIPTION "If true log recent inbound packets."
	DEFVAL { false }
    ::= { arrisRouterSysCfg 34 }

arrisRouterNATPBypassEnable OBJECT-TYPE
    SYNTAX      TruthValue
    MAX-ACCESS  read-write
    STATUS      current
    DESCRIPTION "NATP bypass. When enabled, the NATP acceleration will be disabled."
	DEFVAL { false }
    ::= { arrisRouterSysCfg 35 }

arrisRouterNATDebug OBJECT-TYPE
    SYNTAX      TruthValue
    MAX-ACCESS  read-write
    STATUS      current
    DESCRIPTION "Enable NAT debugging.  This should only be done for troubleshooting purposes.
                A reboot of the device is required for this to take effect.
                Remember to set it back to false when finished troubleshooting."
	DEFVAL { false }
    ::= { arrisRouterSysCfg 36 }

arrisRouterDisableResetButton OBJECT-TYPE
    SYNTAX      TruthValue
    MAX-ACCESS  read-write
    STATUS      current
    DESCRIPTION "If true, the 'reset-to-defaults' functionality, which is triggered when the physical button is depresses, will be disabled."
	DEFVAL { false }
    ::= { arrisRouterSysCfg 37 }


arrisRouterDHCPOption43Sub2 OBJECT-TYPE
    SYNTAX      DisplayString (SIZE (0..32))
    MAX-ACCESS  read-write
    STATUS      current
    DESCRIPTION "Customize the Option 43, sub-option 2 for the eRouter interface on the Media Gateway/Whole Home Solution. Set to '$' to set the option to empty string."
	DEFVAL { "EROUTER" }
    ::= { arrisRouterSysCfg 38 }

arrisRouterDHCPOption43Sub3 OBJECT-TYPE
    SYNTAX      DisplayString (SIZE (0..32))
    MAX-ACCESS  read-write
    STATUS      current
    DESCRIPTION "Customize the Option 43, sub-option 3 for the eRouter interface on the Media Gateway/Whole Home Solution. Set to '$' to set the option to empty string."
	DEFVAL { "ECM:EROUTER" }
    ::= { arrisRouterSysCfg 39 }

arrisRouterESTBDHCPOption43Sub2 OBJECT-TYPE
    SYNTAX      DisplayString (SIZE (0..32))
    MAX-ACCESS  read-write
    STATUS      current
    DESCRIPTION "Customize the Option 43, sub-option 2 for the eSTB interface on the Media Gateway/Whole Home Solution. Set to '$' to set the option to empty string."
	DEFVAL { "ESTB" }
    ::= { arrisRouterSysCfg 40 }

arrisRouterESTBDHCPOption43Sub3 OBJECT-TYPE
    SYNTAX      DisplayString (SIZE (0..32))
    MAX-ACCESS  read-write
    STATUS      current
    DESCRIPTION "Customize the Option 43, sub-option 3 for the eSTB interface on the Media Gateway/Whole Home Solution.  Default value is empty string. Set to '$' to set the option to empty string."
    ::= { arrisRouterSysCfg 41 }

arrisRouterInboundTrafficLogTable OBJECT-TYPE
    SYNTAX      SEQUENCE OF ArrisRouterInboundTrafficLogEntry
    MAX-ACCESS  not-accessible
    STATUS      current
    DESCRIPTION "Table contains recent inbound packet headers."
    ::= { arrisRouterSysCfg 42 }

arrisRouterInboundTrafficLogEntry OBJECT-TYPE
      SYNTAX      ArrisRouterInboundTrafficLogEntry
      MAX-ACCESS  not-accessible
      STATUS      current
      DESCRIPTION "Table contains recent inbound packet headers."
      INDEX { arrisRouterInboundTrafficLogIndex }
      ::= { arrisRouterInboundTrafficLogTable 1 }

ArrisRouterInboundTrafficLogEntry ::= SEQUENCE {
        arrisRouterInboundTrafficLogIndex				Unsigned32,
        arrisRouterInboundTrafficLogData				OCTET STRING
        }
arrisRouterInboundTrafficLogIndex OBJECT-TYPE
     SYNTAX      Unsigned32
     MAX-ACCESS  not-accessible
     STATUS      current
     DESCRIPTION "Index currently limit to 50."
     ::= { arrisRouterInboundTrafficLogEntry 1 }

arrisRouterInboundTrafficLogData OBJECT-TYPE
     SYNTAX      OCTET STRING
     MAX-ACCESS  read-only
     STATUS      current
     DESCRIPTION "Raw IP/UDP/TCP Headers for packet (may have extra bytes beyond headers)"
     ::= { arrisRouterInboundTrafficLogEntry 2 }


arrisRouterClientTrackingEnable OBJECT-TYPE
    SYNTAX      INTEGER { disableAll(0), enableLastSeenUpdate(1), enableLastSeenUpdateAndLogging(2) }
    MAX-ACCESS  read-write
    STATUS      current
    DESCRIPTION "This variable is used to configure the level of LAN client tracking.  To completely disable this feature use disableAll.
                To enable the eRouter to periodically (once per minute) update the value in arrisRouterLanCurrentClientLastSeen use enableLastSeenUpdate.
                To also add logging to track when clients connect and disconnect, use enableLastSeenUpdateAndLogging."
    DEFVAL { enableLastSeenUpdate }
    ::= { arrisRouterSysCfg 43 }

arrisRouterSystemFlags OBJECT-TYPE
     SYNTAX      Integer32
     MAX-ACCESS  read-write
     STATUS      current
     DESCRIPTION "Miscellaneous configuration flags.
                   To disable DHCP requests from the public WAN interface (bcm0) use a value of 8.
                   To disable DHCP requests from the private WAN interface (bcm3) use a value of 16."
     ::= { arrisRouterSysCfg 44 }


arrisRouterNATInfo				 OBJECT IDENTIFIER ::= { arrisRouterSysCfg 45 }

arrisRouterNATPortFwdTable OBJECT-TYPE
    SYNTAX      SEQUENCE OF ArrisRouterNATPortFwdEntry
    MAX-ACCESS  not-accessible
    STATUS      current
	DESCRIPTION  "A table of where each row represents a port forward entry in the NAT table.
                This includes user-configured 'virtual server' entries in addition to dynamically configured entries created via UPnP."
	::= { arrisRouterNATInfo 1 }

arrisRouterNATPortFwdEntry OBJECT-TYPE
    SYNTAX      ArrisRouterNATPortFwdEntry
    MAX-ACCESS  not-accessible
    STATUS      current
	DESCRIPTION  "A table of where each row represents a port forward entry in the NAT table.
                This includes user-configured 'virtual server' entries in addition to dynamically configured entries created via UPnP."
    INDEX   { arrisRouterNATPortFwdIndex }
    ::= { arrisRouterNATPortFwdTable 1 }

ArrisRouterNATPortFwdEntry ::=
    SEQUENCE    {
                arrisRouterNATPortFwdIndex                  Integer32,
                arrisRouterNATPortFwdLocalPortStart         Integer32,
                arrisRouterNATPortFwdLocalPortEnd           Integer32,
                arrisRouterNATPortFwdGlobalPortStart        Integer32,
                arrisRouterNATPortFwdGlobalPortEnd          Integer32,
                arrisRouterNATPortFwdProtocol               INTEGER,
                arrisRouterNATPortFwdDesc                   DisplayString,
                arrisRouterNATPortFwdLocalAddrType          InetAddressType,
                arrisRouterNATPortFwdLocalAddr              InetAddress,
                arrisRouterNATPortFwdRemoteAddrType         InetAddressType,
                arrisRouterNATPortFwdRemoteAddr             InetAddress
            }

arrisRouterNATPortFwdIndex OBJECT-TYPE
    SYNTAX      Integer32 (1..64)
    MAX-ACCESS  not-accessible
    STATUS      current
    DESCRIPTION "Indicates the instance of this table row."
    ::= { arrisRouterNATPortFwdEntry 1 }

arrisRouterNATPortFwdLocalPortStart OBJECT-TYPE
    SYNTAX      Integer32
    MAX-ACCESS  read-only
    STATUS      current
    DESCRIPTION "Start of the range of local ports."
    ::= { arrisRouterNATPortFwdEntry 2 }

arrisRouterNATPortFwdLocalPortEnd OBJECT-TYPE
    SYNTAX      Integer32
    MAX-ACCESS  read-only
    STATUS      current
    DESCRIPTION "End of the range of local ports."
    ::= { arrisRouterNATPortFwdEntry 3 }

arrisRouterNATPortFwdGlobalPortStart OBJECT-TYPE
    SYNTAX      Integer32
    MAX-ACCESS  read-only
    STATUS      current
    DESCRIPTION "Start of the range of Global ports."
    ::= { arrisRouterNATPortFwdEntry 4 }

arrisRouterNATPortFwdGlobalPortEnd OBJECT-TYPE
    SYNTAX      Integer32
    MAX-ACCESS  read-only
    STATUS      current
    DESCRIPTION "End of the range of Global ports."
    ::= { arrisRouterNATPortFwdEntry 5 }

arrisRouterNATPortFwdProtocol OBJECT-TYPE
    SYNTAX      INTEGER { tcp(6), udp(17), both(254) }
    MAX-ACCESS  read-only
    STATUS      current
    DESCRIPTION "Protocol(s) to forward."
    ::= { arrisRouterNATPortFwdEntry 6 }

arrisRouterNATPortFwdDesc OBJECT-TYPE
    SYNTAX      DisplayString
    MAX-ACCESS  read-only
    STATUS      current
    DESCRIPTION "Description of port forwarding entry."
    ::= { arrisRouterNATPortFwdEntry 7 }

arrisRouterNATPortFwdLocalAddrType OBJECT-TYPE
    SYNTAX      InetAddressType
    MAX-ACCESS  read-only
    STATUS      current
    DESCRIPTION "Type (IPv4 or IPv6) of the Local IP address."
    ::= { arrisRouterNATPortFwdEntry 8 }

arrisRouterNATPortFwdLocalAddr OBJECT-TYPE
    SYNTAX      InetAddress
    MAX-ACCESS  read-only
    STATUS      current
    DESCRIPTION "The Local IP address."
    ::= { arrisRouterNATPortFwdEntry 9 }

arrisRouterNATPortFwdRemoteAddrType OBJECT-TYPE
    SYNTAX      InetAddressType
    MAX-ACCESS  read-only
    STATUS      current
    DESCRIPTION "Type (IPv4 or IPv6) of the remote IP address."
    ::= { arrisRouterNATPortFwdEntry 10 }

arrisRouterNATPortFwdRemoteAddr OBJECT-TYPE
    SYNTAX      InetAddress
    MAX-ACCESS  read-only
    STATUS      current
    DESCRIPTION "The remote IP address."
    ::= { arrisRouterNATPortFwdEntry 11 }

arrisRouterNATPortFwdPersistUPnP OBJECT-TYPE
    SYNTAX      TruthValue
    MAX-ACCESS  read-write
    STATUS      current
	DESCRIPTION  "Normally port forwarding entries added using UPnP are NOT persisted to the permanent port forward (virtual servers) list.
                    Set this value to true to persist these entries."
    DEFVAL { false }
	::= { arrisRouterNATInfo 2 }

arrisRouterResetDefaultWebPassword OBJECT-TYPE
     SYNTAX      TruthValue
     MAX-ACCESS  read-write
     STATUS      current
     DESCRIPTION "Resets just the web password to it's default value when set to true. This password will also be reset if arrisRouterDefaults is used"
     ::= { arrisRouterSysCfg 46 }

arrisRouterDHCPOption60ERouter OBJECT-TYPE
    SYNTAX      DisplayString (SIZE (0..32))
    MAX-ACCESS  read-write
    STATUS      current
    DESCRIPTION "Customize the Option 60, for the eROUTER interface on the Media Gateway/Whole Home Solution."
	DEFVAL { "eRouter1.0" }
    ::= { arrisRouterSysCfg 47 }

arrisRouterDHCPOption60ESTB OBJECT-TYPE
    SYNTAX      DisplayString (SIZE (0..32))
    MAX-ACCESS  read-write
    STATUS      current
    DESCRIPTION "Customize the Option 60, for the eSTB interface on the Media Gateway/Whole Home Solution."
	DEFVAL { "eSTB1.0" }
    ::= { arrisRouterSysCfg 48 }

-- Adv debugging

arrisRouterAdvDebug				 OBJECT IDENTIFIER ::= { arrisRouterSysCfg 49 }

arrisRouterAdvDebugEnable OBJECT-TYPE
    SYNTAX      Integer32
    MAX-ACCESS  read-write
    STATUS      current
    DESCRIPTION "Enable advanced debugging features. 0x1 to enable access to arrisRouterSnoopTable, 0x2 to enable access to arrisRouterMsgLogTable.
                Once the values are enabled they can't be disabled using SNMP.  A reboot will restore their default state (off)."
    ::= { arrisRouterAdvDebug 1 }

arrisRouterSnoopTable OBJECT-TYPE
    SYNTAX      SEQUENCE OF ArrisRouterSnoopEntry
    MAX-ACCESS  not-accessible
    STATUS      current
    DESCRIPTION "A table of where each row an eRouter Snoop - this only applies to Broadcom-based eRouter implementations."
	::= { arrisRouterAdvDebug 2 }

arrisRouterSnoopEntry OBJECT-TYPE
    SYNTAX      ArrisRouterSnoopEntry
    MAX-ACCESS  not-accessible
    STATUS      current
    DESCRIPTION  "A table of where each row an eRouter Snoop - this only applies to Broadcom-based eRouter implementations."
    INDEX   { arrisRouterSnoopIndex }
    ::= { arrisRouterSnoopTable 1 }

ArrisRouterSnoopEntry ::=
    SEQUENCE    {
                arrisRouterSnoopIndex               Integer32,
                arrisRouterSnoopStatus              DisplayString,
                arrisRouterSnoopEnabled             TruthValue,
                arrisRouterSnoopDebug               Integer32
                }

arrisRouterSnoopIndex OBJECT-TYPE
    SYNTAX      Integer32 (1..200)
    MAX-ACCESS  not-accessible
    STATUS      current
    DESCRIPTION "Indicates the instance of this table row."
    ::= { arrisRouterSnoopEntry 1 }

arrisRouterSnoopStatus OBJECT-TYPE
    SYNTAX      DisplayString
    MAX-ACCESS  read-only
    STATUS      current
    DESCRIPTION "Displays snoop name, instance value, enabled value, and debug status."
    ::= { arrisRouterSnoopEntry 2 }

arrisRouterSnoopEnabled OBJECT-TYPE
    SYNTAX      TruthValue
    MAX-ACCESS  read-write
    STATUS      current
    DESCRIPTION "Enable or disable the snoop"
    ::= { arrisRouterSnoopEntry 3 }

arrisRouterSnoopDebug OBJECT-TYPE
    SYNTAX      Integer32
    MAX-ACCESS  read-write
    STATUS      current
    DESCRIPTION "Enable or disable snoop debug using a bitmask. Enable debug: 0x1, enable discard debug: 0x2, enable verbose debug: 0x4."
    ::= { arrisRouterSnoopEntry 4 }

arrisRouterMsgLoggingTable OBJECT-TYPE
    SYNTAX      SEQUENCE OF ArrisRouterMsgLoggingEntry
    MAX-ACCESS  not-accessible
    STATUS      current
    DESCRIPTION "A table of where each row an eRouter Logging - this only applies to Broadcom-based eRouter implementations."
    ::= { arrisRouterAdvDebug 3 }

arrisRouterMsgLoggingEntry OBJECT-TYPE
    SYNTAX      ArrisRouterMsgLoggingEntry
    MAX-ACCESS  not-accessible
    STATUS      current
    DESCRIPTION  "A table of where each row an eRouter Logging - this only applies to Broadcom-based eRouter implementations."
    INDEX   { arrisRouterMsgLoggingIndex }
    ::= { arrisRouterMsgLoggingTable 1 }

ArrisRouterMsgLoggingEntry ::=
    SEQUENCE    {
                arrisRouterMsgLoggingIndex      Integer32,
                arrisRouterMsgLoggingStatus     DisplayString,
                arrisRouterMsgLoggingSettings   DisplayString
                }

arrisRouterMsgLoggingIndex OBJECT-TYPE
    SYNTAX      Integer32 (1..600)
    MAX-ACCESS  not-accessible
    STATUS      current
    DESCRIPTION "Indicates the instance of this table row."
    ::= { arrisRouterMsgLoggingEntry 1 }

arrisRouterMsgLoggingStatus OBJECT-TYPE
    SYNTAX      DisplayString
    MAX-ACCESS  read-only
    STATUS      current
    DESCRIPTION "Displays logging name, instance value, enabled value, and debug status."
    ::= { arrisRouterMsgLoggingEntry 2 }

arrisRouterMsgLoggingSettings OBJECT-TYPE
    SYNTAX      DisplayString
    MAX-ACCESS  read-write
    STATUS      current
    DESCRIPTION "Enable or disable the logging severities"
    ::= { arrisRouterMsgLoggingEntry 3 }

arrisRouterAdvDebugSettings OBJECT-TYPE
    SYNTAX      DisplayString
    MAX-ACCESS  read-write
    STATUS      current
    DESCRIPTION "Enable individual component logging.
		The string format allows for 0==off, 1==error, 2==warn, 3==info, 4==superInfo for each component.
		Currently the MG5 only supports one digit for logging for the MAC Mapping manager."
    ::= { arrisRouterAdvDebug 4 }

arrisRouterExtendedOUIList OBJECT-TYPE
    SYNTAX      DisplayString
    MAX-ACCESS  read-write
    STATUS      current
    DESCRIPTION "A comma-delimited list of OUIs that identify Arris MAC address. i.e. 00-15-D1, 00-1D-CD,."
    ::= { arrisRouterSysCfg 50 }

arrisRouterFlashSize OBJECT-TYPE
    SYNTAX       Integer32
    UNITS          "Mega Bytes"
    MAX-ACCESS  read-only
    STATUS      current
    DESCRIPTION "This will return the flash size in Mega Bytes."
    ::= { arrisRouterSysCfg 52 }

arrisRouterDRAMSize OBJECT-TYPE
    SYNTAX      Integer32
    UNITS         "Mega Bytes"
    MAX-ACCESS  read-only
    STATUS      current
    DESCRIPTION "This will return the DRAM size in Mega Bytes."
    ::= { arrisRouterSysCfg 53 }

arrisRouterWirelessBand OBJECT-TYPE
     SYNTAX      INTEGER { unknown(-1), band24GHz(0), band5GHz(1), band24GHzand5GHz(2)}
     MAX-ACCESS  read-only
     STATUS      current
     DESCRIPTION "Get the operating band for Wireless Router.
                   -1: unknown
                    0: 2.4 GHz
                    1: 5.0 GHz
                    2: 2.4 and 5.0 GHz"
     ::= { arrisRouterSysCfg 55}

arrisRouterSaveCurrentConfigFile OBJECT-TYPE
    SYNTAX      INTEGER { save(1) }
    MAX-ACCESS  read-write
    STATUS      current
    DESCRIPTION "Set save(1) to trigger device to save current configuration of Router to a specific file.
                This file will be a snapshot of the changes that have been made to the Router from the user.
                Return save(1) for get operation."
    ::= { arrisRouterSysCfg 57 }

arrisRouterRestoreCurrentConfigFile OBJECT-TYPE
    SYNTAX      INTEGER { restore(1) }
    MAX-ACCESS  read-write
    STATUS      current
    DESCRIPTION "Set restore(1) to trigger device to restore configuration of Router from a specific file.
                This backup file will be used by the Router to restore the user's settings.
                Return restore(1) for get operation."
    ::= { arrisRouterSysCfg 58 }

arrisRouterLocalPosixTimeZone OBJECT-TYPE
    SYNTAX      DisplayString (SIZE(0..255))
    MAX-ACCESS  read-write
    STATUS      current
    DESCRIPTION "The local time zone definition, encoded according to IEEE 1003.1 (POSIX).
                 The following is an example value:
                   EST+5 EDT,M4.1.0/2,M10.5.0/2"
    ::= { arrisRouterSysCfg 59 }

arrisRouterFlashAvailSize OBJECT-TYPE
    SYNTAX       Integer32
    UNITS	   "Mega Bytes"
    MAX-ACCESS  read-only
    STATUS      current
    DESCRIPTION "This will return the flash available memory size in Mega Bytes."
    ::= { arrisRouterSysCfg 60 }

arrisRouterDRAMAvailSize OBJECT-TYPE
    SYNTAX      Integer32
    UNITS	  "Mega Bytes"
    MAX-ACCESS  read-only
    STATUS      current
    DESCRIPTION "This will return the DRAM available memory size in Mega Bytes."
    ::= { arrisRouterSysCfg 61 }

arrisRouterFirstInstallWizardCompletionStatus OBJECT-TYPE
    SYNTAX      TruthValue
    MAX-ACCESS  read-write
    STATUS      current
    DESCRIPTION "If first install wizard is complete returns true otherwise false. GUI should set this MIB to true when first install wizard is complete."
    ::= { arrisRouterSysCfg 62 }

arrisRouterTroubleshooterEnable OBJECT-TYPE
     SYNTAX      TruthValue
     MAX-ACCESS  read-write
     STATUS      current
     DESCRIPTION "Enable/Disable troubleshooting wizard."
     ::= { arrisRouterSysCfg 63 }

arrisRouterCpuSpeed OBJECT-TYPE
    SYNTAX      Integer32
    UNITS         "Mega Hz"
    MAX-ACCESS  read-only
    STATUS      current
    DESCRIPTION "This will return the CPU speed in Mega Hz."
    ::= { arrisRouterSysCfg 64 }

arrisRouterDBConversionStatus OBJECT-TYPE
    SYNTAX      INTEGER { other(0), inprogress(1), complete(2) }
    MAX-ACCESS  read-only
    STATUS      current
    DESCRIPTION "This MIB object reports the current upgrade status of DB conversion."
	DEFVAL { other }
    ::= { arrisRouterSysCfg 65 }

arrisRouterCSRActiveTimeout OBJECT-TYPE
    SYNTAX      Unsigned32
    UNITS       "seconds"
    MAX-ACCESS  read-write
    STATUS      current
    DESCRIPTION "The duration for which CSR login is enabled."
    ::= { arrisRouterSysCfg 66 }

arrisRouterMSOConfigPersistNoPrecedence OBJECT-TYPE
    SYNTAX      TruthValue
    MAX-ACCESS  read-write
    STATUS      current
    DESCRIPTION "true(1) to enable MSO config persist feature, the GW/MoCA settings in CM/XML config file will persist across anything other than a restore to defaults, new config value. This includes reboot. It will persist even after removing the MIB objects from the config file that set the value. The persistent values will be saved into existent post provision persistent file.
      Disabling this MIB requires a factory default to clean up the persistent config values."
    DEFVAL      {false}
    ::= { arrisRouterSysCfg 67 }

arrisRouterFirstInstallRedirectEnable OBJECT-TYPE
    SYNTAX      TruthValue
    MAX-ACCESS  read-write
    STATUS      current
    DESCRIPTION "Enable/Disable the feature to redirect URL request to the first install wizard."
    ::= { arrisRouterSysCfg 68 }

arrisRouterTimeZoneId OBJECT-TYPE
    SYNTAX      Integer32
    MAX-ACCESS  read-write
    STATUS      current
    DESCRIPTION
        "Enumeration for the time zone being configured. The allowed values are:

	Enum 	Description
	0	None
	1	UTC-12  : Kwajalein
	2	UTC-11  : Midway Island, Samoa
	3	UTC-10  : Hawaii
	4	UTC-9   : Alaska
	5	UTC-8   : Pacific Time (USA & Canada)
	6	UTC-7   : Arizona
	7	UTC-7   : Mountain Time (USA & Canada)
	8	UTC-6   : Mexico
	9	UTC-6   : Centra Time (USA & Canada)
	10	UTC-5   : Indiana East, Colombia, Panama
	11	UTC-5   : Eastern Time (USA & Canada)
	12	UTC-4   : Bolivia, Venezuela
	13	UTC-4   : Atlantic Time (Canada), Brazil West
	14	UTC-3.5 : Newfoundland
	15	UTC-3   : Guyana
	16	UTC-3   : Brazil East, Greenland
	17	UTC-2   : Mid-Atlantic
	18	UTC-1   : Azores
	19	UTC+0   : Gambia, Liberia, Morocco
	20	UTC+0   : England
	21	UTC+1   : Tunisia
	22	UTC+1   : France, Germany, Italy
	23	UTC+2   : South Africa
	24	UTC+2   : Greece, Ukraine, Romania, Turkey
	25	UTC+3   : Iraq, Jordan, Kuwait
	26	UTC+4   : Armenia
	27	UTC+5   : Pakistan, Russia
	28	UTC+5.5 : Mumbai, Kolkata, Chennai, New Delhi
	29	UTC+6   : Bangladesh, Russia
	30	UTC+7   : Thailand, Russia
	31	UTC+8   : China, Hong Kong, Australia Western
	32	UTC+8   : Singapore, Taiwan, Russia
	33	UTC+9   : Japan, Korea
	34	UTC+10  : Guam, Russia
	35	UTC+10  : Australia
	36	UTC+11  : Solomon Islands
	37	UTC+12  : Fiji
	38	UTC+12  : New Zealand
	"
    DEFVAL      {0}
    ::= {arrisRouterSysCfg 69 }

arrisRouterDaylightSaving OBJECT-TYPE
    SYNTAX      TruthValue
    MAX-ACCESS  read-write
    STATUS      current
    DESCRIPTION "Enable/Disable automatic adjustment for Daylight Saving Time (DST), if applicable for the timezone selected in arrisRouterTimeZoneId MIB."
    DEFVAL      {false}
    ::= { arrisRouterSysCfg 70 }

-- Settings for enabling SSH and web pages

arrisRouterHostAccessClientSeed OBJECT-TYPE
     SYNTAX OCTET STRING (SIZE (8))
     MAX-ACCESS read-write
     STATUS current
     DESCRIPTION
     "The DES encoded seed--provided by the user--that will be used
      to generate the password of the day for access to the technician web GUI.
      When read, this object will return a zero-length string."
     ::= { arrisRouterHostAccess 1 }

arrisRouterHostCLITimeout OBJECT-TYPE
     SYNTAX      Unsigned32
     MAX-ACCESS  read-write
     STATUS      current
     DESCRIPTION
         "Max time that an SSH session can be idle before it is terminated.
          Range is 0-65535 minutes, where 0 disables the timer completely."
     ::= { arrisRouterHostAccess 2 }

arrisRouterHostAccessSSHEnable OBJECT-TYPE
     SYNTAX INTEGER {
        disableAll(0),
        enableWan(1),
        enableLan(2),
        enableWanLan(3)
     }
     MAX-ACCESS read-write
     STATUS current
     DESCRIPTION
         "Used to turn on/off SSH access. For SSH to be enabled, the
         arrisRouterHostAccessSSHPassword MIB must be set."
     ::= { arrisRouterHostAccess 3 }

arrisRouterHostAccessSSHPassword OBJECT-TYPE
     SYNTAX DisplayString (SIZE(0..11))
     MAX-ACCESS read-write
     STATUS current
     DESCRIPTION "The password required to enable SSH."
     ::= { arrisRouterHostAccess 4 }

arrisRouterWebAccessFreeIdx OBJECT-TYPE
    SYNTAX      Integer32
    MAX-ACCESS  read-only
    STATUS      current
    DESCRIPTION "The lowest available index to that may be used to add a row instance to the arrisRouterWebAccessTable "
    ::= { arrisRouterHostAccess 5 }

arrisRouterWebAccessSetting OBJECT-TYPE
    SYNTAX      INTEGER { disableAll(0), enableLANWeb(1), enableWANWeb(2), enableAllWeb(3) }
    MAX-ACCESS  read-write
    STATUS      current
    DESCRIPTION "Mechanism to enable/disable the access to the entire Web GUI for WAN and/or LAN."
    DEFVAL { enableLANWeb }
    ::= { arrisRouterHostAccess 6 }

arrisRouterWebAccessTable OBJECT-TYPE
     SYNTAX      SEQUENCE OF ArrisRouterWebAccessEntry
     MAX-ACCESS  not-accessible
     STATUS      current
     DESCRIPTION "This table contains access levels for the web pages."
     ::= { arrisRouterHostAccess 7 }

arrisRouterWebAccessEntry OBJECT-TYPE
    SYNTAX      ArrisRouterWebAccessEntry
    MAX-ACCESS  not-accessible
    STATUS      current
	DESCRIPTION "This table contains access levels for the web pages."
    INDEX   { arrisRouterWebAccessIndex }
    ::= { arrisRouterWebAccessTable 1 }

ArrisRouterWebAccessEntry ::=
    SEQUENCE    {
                arrisRouterWebAccessIndex		Integer32,
                arrisRouterWebAccessPage		DisplayString,
                arrisRouterWebAccessLevel		INTEGER,
                arrisRouterWebAccessRowStatus		RowStatus
                }

arrisRouterWebAccessIndex OBJECT-TYPE
     SYNTAX      Integer32 (1..50)
     MAX-ACCESS  not-accessible
     STATUS      current
     DESCRIPTION "Index used to order the arrisRouterWebAccessTable entries."
     ::= { arrisRouterWebAccessEntry 1 }

arrisRouterWebAccessPage OBJECT-TYPE
     SYNTAX      DisplayString
     MAX-ACCESS  read-create
     STATUS      current
     DESCRIPTION "The web page to grant access to.  i.e. router.html or any unique string that identifies a 'screen' or 'page on the web UI."
     ::= { arrisRouterWebAccessEntry 2 }

arrisRouterWebAccessLevel OBJECT-TYPE
     SYNTAX      INTEGER { noAccessAll(0), accessTech(1), accessUser(2), accessAll(3) }
     MAX-ACCESS  read-create
     STATUS      current
     DESCRIPTION "Access level for the web page.
                  NOTE: For TS7.x, this mib only supports (0..2) and value 2 represents accessAll, NOT accessUser."
     ::= { arrisRouterWebAccessEntry 3 }

arrisRouterWebAccessRowStatus OBJECT-TYPE
     SYNTAX     RowStatus
     MAX-ACCESS read-create
     STATUS     current
     DESCRIPTION "For creating new rows."
     ::= { arrisRouterWebAccessEntry 4 }


arrisRouterWebAccessWANACL OBJECT-TYPE
     SYNTAX      DisplayString
     MAX-ACCESS  read-write
     STATUS      current
     DESCRIPTION
        "Access Control List of IPs that can access GUI via global GW WAN
         if empty no access granted to GUI over global GW WAN
         format: ip[-ip](;ip[-ip])*
         example: 10.0.0.0-10.255.255.255;172.44.56.0-172.44.56.244"
     ::= { arrisRouterHostAccess 8 }

arrisRouterSSHAccessWANACL OBJECT-TYPE
     SYNTAX      DisplayString
     MAX-ACCESS  read-write
     STATUS      current
     DESCRIPTION
        "Access Control List of IPs that can access SSH via global WAN
         if empty no access over global WAN
         format: ip[-ip](;ip[-ip])*
         example: 10.0.0.0-10.255.255.255;172.44.56.0-172.44.56.244"
     ::= { arrisRouterHostAccess 9 }

-- for ping

arrisRouterPingTargetAddrType OBJECT-TYPE
    SYNTAX      InetAddressType
    MAX-ACCESS  read-write
    STATUS      current
    DESCRIPTION
        "The type of internet address used for arrisRouterPingTargetAddress.

         This object may be changed while a ping is in progress."
    DEFVAL { ipv4 }
    ::= { arrisRouterPingMgmt 1 }

arrisRouterPingTargetAddress OBJECT-TYPE
    SYNTAX      InetAddress
    MAX-ACCESS  read-write
    STATUS      current
    DESCRIPTION
        "Sets the internet address of the entity to be pinged.  Note that if
         an all-zeros value is specified for this object, then the ping will
         be sent to the default gateway, if one exists.

         This object may be changed while a ping is in progress."
    ::= { arrisRouterPingMgmt 2 }

arrisRouterPingNumPkts OBJECT-TYPE
    SYNTAX      Unsigned32
    MAX-ACCESS  read-write
    STATUS      current
    DESCRIPTION
        "Allows the client to set the number of pings to be sent.  This can be
         set to any number between 1 and (2^32 - 1), or can be set to 'infinite'
         by setting the value to 0.

         Note that if set to infinite, then the ping must be stopped explicitly
         in order to get it to stop.

         This object may be changed while a ping is in progress."
    DEFVAL { 3 }
    ::= { arrisRouterPingMgmt 3 }

arrisRouterPingPktSize OBJECT-TYPE
    SYNTAX      Unsigned32 (64..1518)
    UNITS       "bytes"
    MAX-ACCESS  read-write
    STATUS      current
    DESCRIPTION
        "Allows the client to set the initial size of the ping packets that will
         be sent.  This size includes the LLC header, IP header, ICMP header,
         and the CRC32 at the end.  You must specify values between 64 and 1518,
         which are the min and max size Ethernet frames.

         This object may be changed while a ping is in progress."
    DEFVAL { 64 }
    ::= { arrisRouterPingMgmt 4 }

arrisRouterPingInterval OBJECT-TYPE
    SYNTAX      Unsigned32
    UNITS       "milliseconds"
    MAX-ACCESS  read-write
    STATUS      current
    DESCRIPTION
        "Allows the client to set the amount of time (in milliseconds) that the
         device will sleep before sending a ping.  Generally, this is the time
         between when a ping reply is received and when the next ping will be
         sent.

         Note that the amount of time between sending one ping and sending the
         next ping varies depending on whether or not you enable waiting for
         replies, and how long it takes to receive the reply.

         If waiting for replies is disabled, then this is the time between
         sending one ping and sending the next ping.

         This object may be changed while a ping is in progress."
    DEFVAL { 0 }
    ::= { arrisRouterPingMgmt 5 }

arrisRouterPingTimeout OBJECT-TYPE
    SYNTAX      Integer32 (-1..65535)
    UNITS       "milliseconds"
    MAX-ACCESS  read-write
    STATUS      current
    DESCRIPTION
        "Allows the client to set the amount of time (in milliseconds) that the
         device should wait for a reply after sending a ping.

         If set to any non-negative value, then the device will send a ping and
         wait for a response for the specified amount of time.  Event if
         set to 0, the thread will check for and process a reply packet.

         If set to -1, then the device will not wait at all, and won't even
         check for any replies.

         This object may be changed while a ping is in progress."
    DEFVAL { 5000 }
    ::= { arrisRouterPingMgmt 6 }


arrisRouterPingVerifyReply OBJECT-TYPE
    SYNTAX      TruthValue
    MAX-ACCESS  read-write
    STATUS      current
    DESCRIPTION
        "Enables/disables verification of ping replies.  If enabled, and if
         waiting for replies is enabled, then if a reply is received, it will
         verify that it matches the ping that was sent, and that all of the
         data is intact.

         This object may be changed while a ping is in progress."
    DEFVAL { true }
    ::= { arrisRouterPingMgmt 7 }


arrisRouterPingIpStackNumber OBJECT-TYPE
    SYNTAX      Integer32 (0..8)
    MAX-ACCESS  read-write
    STATUS      current
    DESCRIPTION
        "Allows the client to select the IP stack from which the pings will be
         sent.  Specifying 0 means that the pings will be sent from the same IP
         stack on which this MIB is hosted.

         This object may not be changed while a ping is in progress."
    DEFVAL { 0 }
    ::= { arrisRouterPingMgmt 8 }

arrisRouterPingStartStop OBJECT-TYPE
    SYNTAX      TruthValue
    MAX-ACCESS  read-write
    STATUS      current
    DESCRIPTION
        "Starts or stops the pings, as well as indicating whether a ping is in
         progress when read.  If a ping is already in progress and this object
         is set to true(1), then the ping will continue but the ping statistics
         will be reset.

         This object may be changed while a ping is in progress."
    DEFVAL { true }
    ::= { arrisRouterPingMgmt 9 }

arrisRouterPingPktsSent OBJECT-TYPE
    SYNTAX      Counter32
    MAX-ACCESS  read-only
    STATUS      current
    DESCRIPTION
        "Indicates the number of packets sent since the ping was started."
    ::= { arrisRouterPingMgmt 10 }

arrisRouterPingRepliesReceived OBJECT-TYPE
    SYNTAX      Counter32
    MAX-ACCESS  read-only
    STATUS      current
    DESCRIPTION
        "Indicates the number of replies received since the ping was started."
    ::= { arrisRouterPingMgmt 11 }

arrisRouterPingRepliesVerified OBJECT-TYPE
    SYNTAX      Counter32
    MAX-ACCESS  read-only
    STATUS      current
    DESCRIPTION
        "Indicates the number of replies which were verified since the ping was
         started."
    ::= { arrisRouterPingMgmt 12 }

arrisRouterPingOctetsSent OBJECT-TYPE
    SYNTAX      Counter32
    MAX-ACCESS  read-only
    STATUS      current
    DESCRIPTION
        "Indicates the total number of octets that have been sent in pings
         since the ping was started."
    ::= { arrisRouterPingMgmt 13 }

arrisRouterPingOctetsReceived OBJECT-TYPE
    SYNTAX      Counter32
    MAX-ACCESS  read-only
    STATUS      current
    DESCRIPTION
        "Indicates the total number of octets that have been sent in pings
         since the ping was started."
    ::= { arrisRouterPingMgmt 14 }

arrisRouterPingIcmpErrors OBJECT-TYPE
    SYNTAX      Counter32
    MAX-ACCESS  read-only
    STATUS      current
    DESCRIPTION
        "Indicates the total ICMP errors which have been received since the
         ping was started."
    ::= { arrisRouterPingMgmt 15 }

arrisRouterPingLastIcmpError OBJECT-TYPE
    SYNTAX      Unsigned32
    MAX-ACCESS  read-only
    STATUS      current
    DESCRIPTION
        "Indicates value of the last ICMP error which was received, if any.  If
         there have been no errors, this object will have a value of 0."
    ::= { arrisRouterPingMgmt 16 }

arrisRouterPingAverageRtt OBJECT-TYPE
    SYNTAX      Unsigned32
    UNITS       "milliseconds"
    MAX-ACCESS  read-only
    STATUS      current
    DESCRIPTION
        "The current average ping round-trip-time (RTT)."
    ::= { arrisRouterPingMgmt 17 }

arrisRouterPingMinRtt OBJECT-TYPE
    SYNTAX      Unsigned32
    UNITS       "milliseconds"
    MAX-ACCESS  read-only
    STATUS      current
    DESCRIPTION
        "The minimum ping round-trip-time (RTT) received.  A value
         of 0 for this object implies that no RTT has been received."
    ::= { arrisRouterPingMgmt 18 }

arrisRouterPingMaxRtt OBJECT-TYPE
    SYNTAX      Unsigned32
    UNITS       "milliseconds"
    MAX-ACCESS  read-only
    STATUS      current
    DESCRIPTION
        "The maximum ping round-trip-time (RTT) received.  A value
         of 0 for this object implies that no RTT has been received."
    ::= { arrisRouterPingMgmt 19 }

arrisRouterPingTargetDNSQueryIPAddrType OBJECT-TYPE
    SYNTAX      InetAddressType
    MAX-ACCESS  read-write
    STATUS      current
    DESCRIPTION
        "The protocol version (Ipv4/v6) used for sending DNS query if arrisRouterPingTargetAddressType is DNS."
    DEFVAL { ipv4 }
    ::= { arrisRouterPingMgmt 20 }

arrisRouterPingLog OBJECT-TYPE
    SYNTAX      DisplayString (SIZE (1..255))
    MAX-ACCESS  read-only
    STATUS      current
    DESCRIPTION
        "The ping result log."
    ::= { arrisRouterPingMgmt 21 }

arrisRouterPingDSCP OBJECT-TYPE
    SYNTAX      Unsigned32
    MAX-ACCESS  read-write
    STATUS      current
    DESCRIPTION
        "DiffServ codepoint to be used for the test packets.
         It determines the value of TOS bit in IP header."
    ::= { arrisRouterPingMgmt 22 }

-- traceroute


arrisRouterTraceRtTargAddrType OBJECT-TYPE
    SYNTAX      InetAddressType
    MAX-ACCESS  read-write
    STATUS      current
    DESCRIPTION "The type of internet address used for arrisRouterTraceRtTargetAddress."
    DEFVAL { ipv4 }
    ::= { arrisRouterTraceRtMgmt 1 }

arrisRouterTraceRtTargetAddr OBJECT-TYPE
    SYNTAX      InetAddress
    MAX-ACCESS  read-write
    STATUS      current
    DESCRIPTION "Sets the internet address of the entity for the trace route."
    ::= { arrisRouterTraceRtMgmt 2 }

arrisRouterTraceRtMaxHops OBJECT-TYPE
    SYNTAX      Integer32 (1..65535)
    MAX-ACCESS  read-write
    STATUS      current
    DESCRIPTION "The maximum number of hops for the trace route."
    ::= { arrisRouterTraceRtMgmt 3 }

arrisRouterTraceRtDataSize OBJECT-TYPE
    SYNTAX      Integer32 (1..65535)
    MAX-ACCESS  read-write
    STATUS      current
    DESCRIPTION "The data size of the trace route packet."
    ::= { arrisRouterTraceRtMgmt 4 }

arrisRouterTraceRtResolveHosts OBJECT-TYPE
    SYNTAX      INTEGER { noResolve(0), resolve(1) }
    MAX-ACCESS  read-write
    STATUS      current
    DESCRIPTION "Whether or not to resolve host names."
     DEFVAL		{ resolve }
    ::= { arrisRouterTraceRtMgmt 5 }

arrisRouterTraceRtBasePort OBJECT-TYPE
    SYNTAX      Integer32 (1..65535)
    MAX-ACCESS  read-write
    STATUS      current
    DESCRIPTION "Base port to use for trace route."
    ::= { arrisRouterTraceRtMgmt 6 }

arrisRouterTraceRtStart OBJECT-TYPE
    SYNTAX      INTEGER { traceRouteNotRunning(0), traceRouteRunning(1), startTrace(10), stopTrace(11) }
    MAX-ACCESS  read-write
    STATUS      current
    DESCRIPTION "Start a running trace route.  Will return traceRouteRunning(0) if a trace route is currently running."
    ::= { arrisRouterTraceRtMgmt 7 }

arrisRouterTraceRtLog OBJECT-TYPE
    SYNTAX      DisplayString (SIZE (1..255))
    MAX-ACCESS  read-only
    STATUS      current
    DESCRIPTION "The most recent output log for trace route.  Up to 255 bytes.  Individual lines are separated by a newline."
    ::= { arrisRouterTraceRtMgmt 8 }

arrisRouterTraceRtTimeout OBJECT-TYPE
    SYNTAX      Unsigned32 (1..60)
    UNITS       "seconds"
    MAX-ACCESS  read-write
    STATUS      current
    DESCRIPTION
        "Specifies the time-out value, in seconds, for
         a traceroute request."
    DEFVAL { 3 }
    ::= { arrisRouterTraceRtMgmt 9 }

arrisRouterTraceRtDiffServ OBJECT-TYPE
    SYNTAX      Unsigned32 (0..255)
    MAX-ACCESS  read-write
    STATUS      current
    DESCRIPTION
        "Specifies the value to store in the Type of Service
         (TOS) octet in the IPv4 header or in the Traffic
         Class octet in the IPv6 header, respectively, of the
         IP packet used to encapsulate the traceroute probe.

         The octet to be set in the IP header contains the
         Differentiated Services (DS) Field in the six most
         significant bits.

         This option can be used to determine what effect an
         explicit DS Field setting has on a traceroute response.
         Not all values are legal or meaningful.  A value of 0
         means that the function represented by this option is
         not supported.  DS Field usage is often not supported
         by IP implementations, and not all values are supported.
         Refer to RFC 2474 and RFC 3260 for guidance on usage of
         this field."
    REFERENCE
        "Refer to RFC 1812 for the definition of the IPv4 TOS
         octet and to RFC 2460 for the definition of the IPv6
         Traffic Class octet.  Refer to RFC 2474 and RFC 3260
         for the definition of the Differentiated Services Field."
    DEFVAL { 0 }
    ::= { arrisRouterTraceRtMgmt 10 }

arrisRouterTraceRtNumberofTries OBJECT-TYPE
    SYNTAX      Unsigned32
    MAX-ACCESS  read-write
    STATUS      current
    DESCRIPTION
        "Specifies the number of times packets need to be sent per hop"
    DEFVAL { 3 }
    ::= {arrisRouterTraceRtMgmt 11 }

arrisRouterICtrlPortMapCount OBJECT-TYPE
    SYNTAX      Integer32
    MAX-ACCESS  read-only
    STATUS      current
    DESCRIPTION "Count of the rows in the table: arrisRouterICtrlPortMapTable."
    ::= { arrisRouterICtrl 1 }

arrisRouterICtrlPortMapTable OBJECT-TYPE
     SYNTAX      SEQUENCE OF ArrisRouterICtrlPortMapEntry
     MAX-ACCESS  not-accessible
     STATUS      current
     DESCRIPTION "This table contains IP port mappings."
     ::= { arrisRouterICtrl 2 }

arrisRouterICtrlPortMapEntry OBJECT-TYPE
    SYNTAX      ArrisRouterICtrlPortMapEntry
    MAX-ACCESS  not-accessible
    STATUS      current
    DESCRIPTION "This table contains IP port mappings."
    INDEX   { arrisRouterICtrlPortMapIndex }
    ::= { arrisRouterICtrlPortMapTable 1 }

ArrisRouterICtrlPortMapEntry ::=
    SEQUENCE    {
                arrisRouterICtrlPortMapIndex                Integer32,
                arrisRouterPortMapDescription               DisplayString,
                arrisRouterPortMapInternalClientAddrType    InetAddressType,
                arrisRouterPortMapInternalClientAddr        InetAddress,
                arrisRouterPortMapProtocol                  INTEGER,
                arrisRouterPortMapExternalPort              Unsigned32,
                arrisRouterPortMapInternalPort              Unsigned32,
                arrisRouterPortMapRowStatus                 RowStatus,
                arrisRouterPortMapInternalStartPort         Unsigned32,
                arrisRouterPortMapInternalEndPort           Unsigned32,
                arrisRouterPortMapExternalStartPort         Unsigned32,
                arrisRouterPortMapExternalEndPort           Unsigned32
                }

arrisRouterICtrlPortMapIndex OBJECT-TYPE
     SYNTAX      Integer32 (1..255)
     MAX-ACCESS  not-accessible
     STATUS      current
     DESCRIPTION "Table index."
     ::= { arrisRouterICtrlPortMapEntry 1 }

arrisRouterPortMapDescription OBJECT-TYPE
     SYNTAX      DisplayString
     MAX-ACCESS  read-create
     STATUS      current
     DESCRIPTION "Provides a descriptive human-readable string explaining the
                  usage of the port mapping. For example, Port 80 might be represented as
                  Web Server. The max length is 128 bytes."
     ::= { arrisRouterICtrlPortMapEntry 2 }

arrisRouterPortMapInternalClientAddrType OBJECT-TYPE
     SYNTAX     InetAddressType
     MAX-ACCESS  read-create
     STATUS      current
     DESCRIPTION  "This is the IP address type of the destination host that traffic assigned to this port from the WAN will be mapped to on the LAN."
     ::= { arrisRouterICtrlPortMapEntry 3 }

arrisRouterPortMapInternalClientAddr OBJECT-TYPE
     SYNTAX     InetAddress
     MAX-ACCESS  read-create
     STATUS      current
     DESCRIPTION  "This is the IP address of the destination host that traffic assigned to this port from the WAN will be mapped to on the LAN."
     ::= { arrisRouterICtrlPortMapEntry 4 }

arrisRouterPortMapProtocol OBJECT-TYPE
     SYNTAX      INTEGER { tcp(1), udp(2) }
     MAX-ACCESS  read-create
     STATUS      current
     DESCRIPTION "Can be 'UDP' or 'TCP'. Used to set the specific IP protocol type that this port is mapped for."
     DEFVAL { tcp }
     ::= { arrisRouterICtrlPortMapEntry 5 }

arrisRouterPortMapExternalPort  OBJECT-TYPE
     SYNTAX      Unsigned32
     MAX-ACCESS  read-create
     STATUS      current
     DESCRIPTION "The port number that an external host will connect to on the WAN side of the router that will be mapped."
     ::= { arrisRouterICtrlPortMapEntry 6 }

arrisRouterPortMapInternalPort  OBJECT-TYPE
     SYNTAX      Unsigned32
     MAX-ACCESS  read-create
     STATUS      current
     DESCRIPTION "port number that will be used on the destination host."
     ::= { arrisRouterICtrlPortMapEntry 7 }

arrisRouterPortMapRowStatus OBJECT-TYPE
     SYNTAX     RowStatus
     MAX-ACCESS read-create
     STATUS     current
     DESCRIPTION "For creating new rows."
     ::= { arrisRouterICtrlPortMapEntry 8 }

arrisRouterPortMapInternalStartPort OBJECT-TYPE
     SYNTAX      Unsigned32
     MAX-ACCESS  read-create
     STATUS      current
     DESCRIPTION "start port number that will be used on the destination host."
     ::= { arrisRouterICtrlPortMapEntry 9 }

arrisRouterPortMapInternalEndPort OBJECT-TYPE
     SYNTAX      Unsigned32
     MAX-ACCESS  read-create
     STATUS      current
     DESCRIPTION "end port number that will be used on the destination host."
     ::= { arrisRouterICtrlPortMapEntry 10 }

arrisRouterPortMapExternalStartPort  OBJECT-TYPE
     SYNTAX      Unsigned32
     MAX-ACCESS  read-create
     STATUS      current
     DESCRIPTION "The start port number that an external host will connect to on the WAN side of the router that will be mapped."
     ::= { arrisRouterICtrlPortMapEntry 11 }

arrisRouterPortMapExternalEndPort  OBJECT-TYPE
     SYNTAX      Unsigned32
     MAX-ACCESS  read-create
     STATUS      current
     DESCRIPTION "The end port number that an external host will connect to on the WAN side of the router that will be mapped."
     ::= { arrisRouterICtrlPortMapEntry 12 }

arrisRouterICtrlGetDeviceSettings                 OBJECT IDENTIFIER ::= { arrisRouterICtrl 3 }
arrisRouterICtrlIsDeviceReady                     OBJECT IDENTIFIER ::= { arrisRouterICtrl 4 }
arrisRouterICtrlReboot                            OBJECT IDENTIFIER ::= { arrisRouterICtrl 5 }
arrisRouterICtrlSetDeviceSettings                 OBJECT IDENTIFIER ::= { arrisRouterICtrl 6 }
arrisRouterICtrlRouterSettings                    OBJECT IDENTIFIER ::= { arrisRouterICtrl 7 }
arrisRouterICtrlWLanRadioSettings                 OBJECT IDENTIFIER ::= { arrisRouterICtrl 8 }
arrisRouterICtrlSetBridgeConnect                  OBJECT IDENTIFIER ::= { arrisRouterICtrl 9 }
arrisRouterICtrlGetWanSettings                    OBJECT IDENTIFIER ::= { arrisRouterICtrl 10 }

arrisRouterICtrlDeviceSettingsFWversion OBJECT-TYPE
     SYNTAX      DisplayString
     MAX-ACCESS  read-only
     STATUS      current
     DESCRIPTION "The Firmware Version."
     ::= { arrisRouterICtrlGetDeviceSettings 1 }


arrisRouterICtrlDeviceStatus OBJECT-TYPE
     SYNTAX      INTEGER { error(0), ok(1) }
     MAX-ACCESS  read-only
     STATUS      current
     DESCRIPTION "This method is used to determine if a given device is ready to process HNAP calls.
                  It can be used in a reboot sequence, so that an HNAP client knows when an HNAP server has completed rebooting and is
                  ready to begin processing commands again. If the device returns OK, it must be available to respond to
                  additional requests until further state changes are made.
		  NOTE: For TS7.x, this mib has read-write access property."
     ::= { arrisRouterICtrlIsDeviceReady 1 }

arrisRouterICtrlInitiateReboot OBJECT-TYPE
     SYNTAX      INTEGER { reboot(1) }
     MAX-ACCESS  read-write
     STATUS      current
     DESCRIPTION "Initiate a reboot."
     ::= { arrisRouterICtrlReboot 1 }


arrisRouterICtrlSetDeviceName OBJECT-TYPE
     SYNTAX      DisplayString
     MAX-ACCESS  read-write
     STATUS      current
     DESCRIPTION "A user-readable friendly name to use for this device. This name is used for the following:
                    End users associate this name with devices when displayed by device management software (for example,
                        the icon that displays in Network Magic's network map for this device).
                    You should use it for DHCP leases and other network identification."
     ::= { arrisRouterICtrlSetDeviceSettings 1 }

arrisRouterICtrlSetAdminPassword OBJECT-TYPE
     SYNTAX      DisplayString
     MAX-ACCESS  read-write
     STATUS      current
     DESCRIPTION "The administrator password for this device."
     ::= { arrisRouterICtrlSetDeviceSettings 2 }


arrisRouterICtrlRouterManageRemote OBJECT-TYPE
     SYNTAX      TruthValue
     MAX-ACCESS  read-write
     STATUS      current
     DESCRIPTION "Indicates if remote management is enabled for this device.
                    true: the administrative interface and HNAP interfaces are
                            accessible from the WAN side of the router.
                    false: the administrative interface and HNAP interfaces are
                            only accessible from the LAN side of the router."
     ::= { arrisRouterICtrlRouterSettings 1 }

arrisRouterICtrlRouterRemotePort OBJECT-TYPE
     SYNTAX      Unsigned32
     MAX-ACCESS  read-write
     STATUS      current
     DESCRIPTION "Returns the port number that can be used to access the router management interface from the WAN side."
     ::= { arrisRouterICtrlRouterSettings 2 }

arrisRouterICtrlRouterRemoteSSL OBJECT-TYPE
     SYNTAX      TruthValue
     MAX-ACCESS  read-write
     STATUS      current
     DESCRIPTION "Indicates if the secure SSL port is available for this device.
                    true: the remote port specified by RemotePort will ONLY accept SSL connections.
                    false: the remote port specified by RemotePort will NOT accept SSL connections."
     ::= { arrisRouterICtrlRouterSettings 3 }


arrisRouterICtrlWLanRadioMacAddress OBJECT-TYPE
     SYNTAX      MacAddress
     MAX-ACCESS  read-write
     STATUS      current
     DESCRIPTION "The MAC address for this interface. The device will still return this, even if the WLAN interface is currently disabled."
     ::= { arrisRouterICtrlWLanRadioSettings 1 }

arrisRouterICtrlWLanRadioChannelWidth OBJECT-TYPE
     SYNTAX      Unsigned32
     MAX-ACCESS  read-write
     STATUS      current
     DESCRIPTION "Width of each channel. This corresponds to the 802.11n channel width standard. Valid values are:
                    0: Automatic
                    20: 20 MHz channel width
                    40: 40 MHz channel width
                    Notes:
                        If a router is configured in Automatic selection mode it
                            should return 0 to indicate this.
                        It is not possible for an HNAP client to interrogate the
                            currently selected channel width of a router configured in
                            automatic mode."
     ::= { arrisRouterICtrlWLanRadioSettings 2 }


arrisRouterICtrlSetBridgeEthernetPort OBJECT-TYPE
     SYNTAX      Unsigned32
     MAX-ACCESS  read-write
     STATUS      current
     DESCRIPTION "The parameter 'EthernetPort' determines which physical Ethernet LAN
                    port is able to accept bridged traffic.  This port must correspond to the physically
                    numbered ports on the device."
     ::= { arrisRouterICtrlSetBridgeConnect 1 }

arrisRouterICtrlSetBridgeMinutes OBJECT-TYPE
     SYNTAX      Unsigned32
     MAX-ACCESS  read-write
     STATUS      current
     DESCRIPTION "The parameter 'Minutes' specifies the maximum amount of time the bridge is to remain active after which the bridge is immediately closed without warning,
                 secondary calls to SetBridgeConnect that specify the same port and time value should update the existing timeout value to be based on the time of the
                 latest call with the latest timeout value (and should not close the bridge for any reason)"
     ::= { arrisRouterICtrlSetBridgeConnect 2 }

arrisRouterICtrlSetBridgePermanentPort4Enable OBJECT-TYPE
     SYNTAX      TruthValue
     MAX-ACCESS  read-write
     STATUS      current
     DESCRIPTION "Set the port 4 to permanent bridge mode. Default value is false. If this MIB is enabled, it overrides the other two ICtrlSetBridge mibs(arrisRouterICtrlSetBridgeEthernetPort and
     arrisRouterICtrlSetBridgeMinutes), and it ignores HNAP related configuration commands (but responds OK to the device)."
     DEFVAL { false }
     ::= { arrisRouterICtrlSetBridgeConnect 3 }

arrisRouterICtrlGetWanType OBJECT-TYPE
     SYNTAX      DisplayString
     MAX-ACCESS  read-write
     STATUS      current
     DESCRIPTION "The type of configuration. Can be one of the following values, depending on the WAN configurations supported by the device.
                    BigPond
                    DHCP
                    DHCPPPPoE
                    DynamicL2TP
                    DynamicPPTP
                    Static
                    StaticL2TP
                    StaticPPPoE
                    StaticPPTP
                    BridgedOnly
                    Static1483Bridged
                    Dynamic1483Bridged
                    Static1483Routed
                    StaticPPPOA
                    DynamicPPPOA."
    DEFVAL { "DHCP" }
     ::= { arrisRouterICtrlGetWanSettings 2 }

arrisRouterICtrlGetWanMTU OBJECT-TYPE
     SYNTAX      Unsigned32
     MAX-ACCESS  read-write
     STATUS      current
     DESCRIPTION "The maximum packet size (maximum transmission unit (MTU)) in octets.
                  This cannot exceed what the router supports (that is, the MTU value that the router provides in response to a GETxxx method)."
     ::= { arrisRouterICtrlGetWanSettings 3 }

arrisRouterICtrlGetWanPrefixLen OBJECT-TYPE
     SYNTAX      InetAddressPrefixLength
     MAX-ACCESS  read-write
     STATUS      current
     DESCRIPTION "The prefix (netmask) for the Wan connection."
     ::= { arrisRouterICtrlGetWanSettings 4 }

arrisRouterICtrlGetWanGatewayAddrType OBJECT-TYPE
     SYNTAX      InetAddressType
     MAX-ACCESS  read-write
     STATUS      current
     DESCRIPTION "The type for the gateway IP address for this router."
     ::= { arrisRouterICtrlGetWanSettings 5 }

arrisRouterICtrlGetWanGatewayAddr OBJECT-TYPE
     SYNTAX      InetAddress
     MAX-ACCESS  read-write
     STATUS      current
     DESCRIPTION "The the gateway IP address for this router.
                     If Type is set to DHCP, DHCPPPPoE, DynamicPPPOA or Dynamic1483Bridged this returns the DHCPconfigured values.
                     If DHCP has not acquired an address yet, this should return 0.0.0.0 (for IPv4) or the equivalent IPv6 unconfigured IP address."
     ::= { arrisRouterICtrlGetWanSettings 6 }

arrisRouterICtrlGetWanDNSPrimaryAddrType OBJECT-TYPE
     SYNTAX      InetAddressType
     MAX-ACCESS  read-write
     STATUS      current
     DESCRIPTION "The type for the DNS address."
     ::= { arrisRouterICtrlGetWanSettings 7 }

arrisRouterICtrlGetWanDNSPrimaryAddr OBJECT-TYPE
     SYNTAX      InetAddress
     MAX-ACCESS  read-write
     STATUS      current
     DESCRIPTION "The DNS primary setting for this router.
                    If DHCP is being used as the WAN Type, a device should
                    return DNS settings it may have obtained from the DHCP
                    lease. Both DNS settings may be blank in the event that there
                    is no current lease.
                    For non-DHCP WAN Types, these settings should always be
                    valid."
     ::= { arrisRouterICtrlGetWanSettings 8 }

arrisRouterICtrlGetWanDNSSecondaryAddrType OBJECT-TYPE
     SYNTAX      InetAddressType
     MAX-ACCESS  read-write
     STATUS      current
     DESCRIPTION "The type for the DNS address."
     ::= { arrisRouterICtrlGetWanSettings 9 }

arrisRouterICtrlGetWanDNSSecondaryAddr OBJECT-TYPE
     SYNTAX      InetAddress
     MAX-ACCESS  read-write
     STATUS      current
     DESCRIPTION "The DNS secondary setting for this router.
                    If DHCP is being used as the WAN Type, a device should
                    return DNS settings it may have obtained from the DHCP
                    lease. Both DNS settings may be blank in the event that there
                    is no current lease.
                    For non-DHCP WAN Types, these settings should always be
                    valid."
     ::= { arrisRouterICtrlGetWanSettings 10 }

arrisRouterICtrlGetWanMacAddress OBJECT-TYPE
     SYNTAX      MacAddress
     MAX-ACCESS  read-write
     STATUS      current
     DESCRIPTION "The MAC address for the WAN interface."
     ::= { arrisRouterICtrlGetWanSettings 11 }

arrisRouterICtrlHNAPServerPort OBJECT-TYPE
     SYNTAX      Unsigned32
     MAX-ACCESS  read-write
     STATUS      current
     DESCRIPTION "The port used by the internal HNAP server to receive messages from the HNAP client."
     DEFVAL { 8081 }
     ::= { arrisRouterICtrl 11 }

arrisRouterICtrlEnable OBJECT-TYPE
     SYNTAX      INTEGER { disabled(0), enabled(1) }
     MAX-ACCESS  read-write
     STATUS      current
     DESCRIPTION "Enable or disable the IControl Module, default is disabled."
         DEFVAL { disabled }
     ::= { arrisRouterICtrl 12 }

arrisRouterICtrlHashingKey OBJECT-TYPE
     SYNTAX      DisplayString (SIZE (1..127))
     MAX-ACCESS  read-write
     STATUS      current
     DESCRIPTION "Set hashing key for IControl feature to calculate the wpa psk."
     ::= { arrisRouterICtrl 13 }

arrisRouterICtrlPortMapTableEnabled OBJECT-TYPE
    SYNTAX      TruthValue
    MAX-ACCESS  read-write
    STATUS      current
    DESCRIPTION "Indicates whether iCtrl Port Mapping is enabled."
        DEFVAL { true }
    ::= { arrisRouterICtrl 14 }

arrisRouterFlapListCfg			OBJECT IDENTIFIER ::= { arrisRouterMibObjects 11 }

-- Client Flap List

arrisRouterFlapListEnable OBJECT-TYPE
    SYNTAX      TruthValue
    MAX-ACCESS  read-write
    STATUS      current
    DESCRIPTION "Is the Flap List enabled or not"
    DEFVAL { false }
    ::= { arrisRouterFlapListCfg 1 }

arrisRouterFlapListWLANInterval OBJECT-TYPE
    SYNTAX          Integer32 (0..3600)
    MAX-ACCESS  	read-write
    STATUS      	current
    DESCRIPTION		"Minimum number of Seconds between subsequent WLAN Associations
                     from the same client in order to mark it as flapping"
    DEFVAL { 120 }
    ::= { arrisRouterFlapListCfg 2 }

arrisRouterFlapListDHCPInterval OBJECT-TYPE
    SYNTAX          Integer32 (0..3600)
    MAX-ACCESS  	read-write
    STATUS      	current
    DESCRIPTION		"Minimum number of Seconds between subsequent DHCP Requests
                     from the same client in order to mark it as flapping"
    DEFVAL { 300 }
    ::= { arrisRouterFlapListCfg 3 }

arrisRouterFlapListReportPeroid OBJECT-TYPE
    SYNTAX          Integer32 (0..86400)
    MAX-ACCESS  	read-write
    STATUS      	current
    DESCRIPTION		"Maximum Number of Seconds to maintian a client in the Flap List."
    DEFVAL { 86400 }
    ::= { arrisRouterFlapListCfg 4 }

arrisRouterFlapListWLANCount OBJECT-TYPE
    SYNTAX      Integer32
    MAX-ACCESS  read-only
    STATUS      current
    DESCRIPTION "Total Number of WLAN Clients in the WLAN Flap List."
    ::= { arrisRouterFlapListCfg 5 }

arrisRouterFlapListLANCount OBJECT-TYPE
    SYNTAX      Integer32
    MAX-ACCESS  read-only
    STATUS      current
    DESCRIPTION "Total Number of LAN Clients in the LAN Flap List"
    ::= { arrisRouterFlapListCfg 6 }

arrisRouterFlapListReqFreqThreshold OBJECT-TYPE
    SYNTAX      Integer32 (0..255)
    MAX-ACCESS  read-write
    STATUS      current
    DESCRIPTION "Minimum number of flap count that determines the client is flapping"
    ::= { arrisRouterFlapListCfg 7 }

-- WLAN Flap List Entry Table

arrisRouterFlapListWLANTable  OBJECT-TYPE
    SYNTAX      SEQUENCE OF ArrisRouterFlapListWLANEntry
    MAX-ACCESS  not-accessible
    STATUS      current
    DESCRIPTION   "A table of WLAN Flapping Clients"
    ::= { arrisRouterFlapListCfg 10 }

arrisRouterFlapListWLANEntry OBJECT-TYPE
    SYNTAX      ArrisRouterFlapListWLANEntry
    MAX-ACCESS  not-accessible
    STATUS      current
    DESCRIPTION   "A table of WLAN Flap List Clients"
    INDEX   { arrisRouterFlapListWLANIndex }
    ::= { arrisRouterFlapListWLANTable 1 }

ArrisRouterFlapListWLANEntry ::=
        SEQUENCE    {
		arrisRouterFlapListWLANIndex			Unsigned32,
		arrisRouterFlapListWLANMacAddress 		MacAddress,
		arrisRouterFlapListWLANRemoveTime		DateAndTime,
		arrisRouterFlapListWLANFlapTime   		DateAndTime
        }

arrisRouterFlapListWLANIndex OBJECT-TYPE
    SYNTAX      Unsigned32 (0..64)
    MAX-ACCESS  not-accessible
    STATUS      current
    DESCRIPTION
        "Indicates the instance of this table row."
    ::= { arrisRouterFlapListWLANEntry 1 }

arrisRouterFlapListWLANMacAddress OBJECT-TYPE
    SYNTAX      MacAddress
    MAX-ACCESS  read-only
    STATUS      current
    DESCRIPTION
        "A MAC address of a WLAN station which has flapped."
    ::= { arrisRouterFlapListWLANEntry 2 }

arrisRouterFlapListWLANRemoveTime OBJECT-TYPE
    SYNTAX      DateAndTime
    MAX-ACCESS  read-only
    STATUS      current
    DESCRIPTION "The date and time when this Client Last Flapped."
    ::= { arrisRouterFlapListWLANEntry 3 }

arrisRouterFlapListWLANFlapTime OBJECT-TYPE
    SYNTAX      DateAndTime
    MAX-ACCESS  read-only
    STATUS      current
    DESCRIPTION "The date and time when this Client can be removed from the List."
    ::= { arrisRouterFlapListWLANEntry 4 }

-- LAN Flap List Entry Table

arrisRouterFlapListLANTable  OBJECT-TYPE
    SYNTAX      SEQUENCE OF ArrisRouterFlapListLANEntry
    MAX-ACCESS  not-accessible
    STATUS      current
    DESCRIPTION   "A table of LAN Flapping Clients"
    ::= { arrisRouterFlapListCfg 11 }

arrisRouterFlapListLANEntry OBJECT-TYPE
    SYNTAX      ArrisRouterFlapListLANEntry
    MAX-ACCESS  not-accessible
    STATUS      current
    DESCRIPTION   "A table of LAN Flap List Clients"
    INDEX   { arrisRouterFlapListLANIndex }
    ::= { arrisRouterFlapListLANTable 1 }

ArrisRouterFlapListLANEntry ::=
        SEQUENCE    {
		arrisRouterFlapListLANIndex		Unsigned32,
		arrisRouterFlapListLANMacAddress       	MacAddress,
		arrisRouterFlapListLANRemoveTime   	DateAndTime,
		arrisRouterFlapListLANFlapTime   	DateAndTime
        }

arrisRouterFlapListLANIndex OBJECT-TYPE
    SYNTAX      Unsigned32 (0..64)
    MAX-ACCESS  not-accessible
    STATUS      current
    DESCRIPTION
        "Indicates the instance of this table row."
    ::= { arrisRouterFlapListLANEntry 1 }

arrisRouterFlapListLANMacAddress OBJECT-TYPE
    SYNTAX      MacAddress
    MAX-ACCESS  read-only
    STATUS      current
    DESCRIPTION
        "The MAC address of a LAN Client which has flapped."
    ::= { arrisRouterFlapListLANEntry 2 }

arrisRouterFlapListLANRemoveTime OBJECT-TYPE
    SYNTAX      DateAndTime
    MAX-ACCESS  read-only
    STATUS      current
    DESCRIPTION "The date and time when this Client Entry can be removed"
    ::= { arrisRouterFlapListLANEntry 3 }

arrisRouterFlapListLANFlapTime OBJECT-TYPE
    SYNTAX      DateAndTime
    MAX-ACCESS  read-only
    STATUS      current
    DESCRIPTION "The date and time when this Client Last Flapped."
    ::= { arrisRouterFlapListLANEntry 4 }

arrisRouterUsbConfig       OBJECT IDENTIFIER ::= { arrisRouterMibObjects 12 }
-- USB config

-- USB access control
arrisRouterUsbEnableAccessCtrl OBJECT-TYPE
    SYNTAX      TruthValue
    MAX-ACCESS  read-write
    STATUS      current
    DESCRIPTION "enable/disable access control"
    DEFVAL     { false }
    ::= { arrisRouterUsbConfig 1 }

-- USB status table
arrisRouterUsbStatusTable  OBJECT-TYPE
    SYNTAX      SEQUENCE OF ArrisRouterUsbStatusEntry
    MAX-ACCESS  not-accessible
    STATUS      current
    DESCRIPTION   "A table of USB status"
    ::= { arrisRouterUsbConfig 2}

arrisRouterUsbStatusEntry OBJECT-TYPE
    SYNTAX      ArrisRouterUsbStatusEntry
    MAX-ACCESS  not-accessible
    STATUS      current
    DESCRIPTION   "A table of USB status"
    INDEX   { arrisRouterUsbStatusIndex }
    ::= { arrisRouterUsbStatusTable 1 }

ArrisRouterUsbStatusEntry ::=
        SEQUENCE    {
                arrisRouterUsbStatusIndex                     Unsigned32,
                arrisRouterUsbstatusRowstatus     RowStatus,
                arrisRouterUsbVolName             DisplayString,
                arrisRouterUsbTotalSpace          DisplayString,
                arrisRouterUsbFreeSpace           DisplayString,
                arrisRouterUsbFileSystem          INTEGER,
                arrisRouterUsbApproved            TruthValue,
                arrisRouterUsbIsOnline            TruthValue
        }

arrisRouterUsbStatusIndex OBJECT-TYPE
    SYNTAX      Unsigned32 (1..32)
    MAX-ACCESS  not-accessible
    STATUS      current
    DESCRIPTION "Table index"
    ::= { arrisRouterUsbStatusEntry 1 }

arrisRouterUsbstatusRowstatus OBJECT-TYPE
    SYNTAX      RowStatus
    MAX-ACCESS  read-create
    STATUS      current
    DESCRIPTION "RowStatus used to add/remove rows from the table"
    ::= { arrisRouterUsbStatusEntry 2 }

arrisRouterUsbVolName OBJECT-TYPE
    SYNTAX      DisplayString (SIZE (0..64))
    MAX-ACCESS  read-only
    STATUS      current
    DESCRIPTION "USB volume name"
    ::= { arrisRouterUsbStatusEntry 3 }

arrisRouterUsbTotalSpace OBJECT-TYPE
    SYNTAX      DisplayString (SIZE (0..64))
    MAX-ACCESS  read-only
    STATUS      current
    DESCRIPTION "USB total space"
    ::= { arrisRouterUsbStatusEntry 4 }

arrisRouterUsbFreeSpace OBJECT-TYPE
    SYNTAX      DisplayString (SIZE (0..64))
    MAX-ACCESS  read-only
    STATUS      current
    DESCRIPTION "USB free space"
    ::= { arrisRouterUsbStatusEntry 5 }

arrisRouterUsbFileSystem OBJECT-TYPE
    SYNTAX      INTEGER { ntfs(0), hfs(1), fat32(2), fat(3), linux(4), gpt(5), extended(6), unknown(7)}
    MAX-ACCESS  read-only
    STATUS      current
    DESCRIPTION "USB device file system"
    DEFVAL { ntfs }
    ::= { arrisRouterUsbStatusEntry 6 }

arrisRouterUsbApproved OBJECT-TYPE
    SYNTAX      TruthValue
    MAX-ACCESS  read-only
    STATUS      current
    DESCRIPTION "enable/disable share folder"
    DEFVAL     { false }
    ::= { arrisRouterUsbStatusEntry 7 }

arrisRouterUsbIsOnline OBJECT-TYPE
    SYNTAX      TruthValue
    MAX-ACCESS  read-only
    STATUS      current
    DESCRIPTION "Check USB Online/Offline"
    DEFVAL     { false }
    ::= { arrisRouterUsbStatusEntry 8 }

--file sharing table

arrisRouterUsbFileSharingObjs           OBJECT IDENTIFIER ::= { arrisRouterUsbConfig 3 }

arrisRouterUsbFtpEnable OBJECT-TYPE
    SYNTAX      TruthValue
    MAX-ACCESS  read-write
    STATUS      current
    DESCRIPTION "enable/disable ftp"
    DEFVAL     { false }
    ::= { arrisRouterUsbFileSharingObjs 1 }

arrisRouterUsbftpServer OBJECT-TYPE
    SYNTAX      DisplayString (SIZE (0..64))
    MAX-ACCESS  read-only
    STATUS      current
    DESCRIPTION "FTP server"
    ::= { arrisRouterUsbFileSharingObjs 2 }

arrisRouterUsbShareFolderEnable OBJECT-TYPE
    SYNTAX      TruthValue
    MAX-ACCESS  read-write
    STATUS      current
    DESCRIPTION "enable/disable share folder"
    DEFVAL     { false }
    ::= { arrisRouterUsbFileSharingObjs 3 }

arrisRouterUsbShareFolderAddr OBJECT-TYPE
    SYNTAX      DisplayString (SIZE (0..64))
    MAX-ACCESS  read-only
    STATUS      current
    DESCRIPTION "share folder address"
    ::= { arrisRouterUsbFileSharingObjs 4 }

arrisRouterUsbShareFolderTable  OBJECT-TYPE
    SYNTAX      SEQUENCE OF ArrisRouterUsbShareFolderEntry
    MAX-ACCESS  not-accessible
    STATUS      current
    DESCRIPTION   "A table of sharing folder"
    ::= { arrisRouterUsbFileSharingObjs 5}

arrisRouterUsbShareFolderEntry OBJECT-TYPE
    SYNTAX      ArrisRouterUsbShareFolderEntry
    MAX-ACCESS  not-accessible
    STATUS      current
    DESCRIPTION   "A table of sharing folder"
    INDEX   { arrisRouterUsbShareFolderIndex }
    ::= { arrisRouterUsbShareFolderTable 1 }

ArrisRouterUsbShareFolderEntry ::=
        SEQUENCE    {
                arrisRouterUsbShareFolderIndex            Unsigned32,
                arrisRouterUsbShareFolderRowstatus  RowStatus,
                arrisRouterUsbShareVolumeName       DisplayString,
                arrisRouterUsbShareFloderName           DisplayString,
                arrisRouterUsbShareName             DisplayString,
                arrisRouterUsbShareAdminAccess      TruthValue,
                arrisRouterUsbShareEveryAccess      TruthValue,
                arrisRouterUsbShareSN             DisplayString,
                arrisRouterUsbDefaultRule       TruthValue,
                arrisRouterUsbShareStatus      Unsigned32
        }

arrisRouterUsbShareFolderIndex OBJECT-TYPE
    SYNTAX      Unsigned32 (1..64)
    MAX-ACCESS  not-accessible
    STATUS      current
    DESCRIPTION "Table index"
    ::= { arrisRouterUsbShareFolderEntry 1 }

arrisRouterUsbShareFolderRowstatus OBJECT-TYPE
    SYNTAX      RowStatus
    MAX-ACCESS  read-create
    STATUS      current
    DESCRIPTION "RowStatus used to add/remove rows from the table"
    ::= { arrisRouterUsbShareFolderEntry 2 }

arrisRouterUsbShareVolumeName OBJECT-TYPE
    SYNTAX      DisplayString (SIZE (0..64))
    MAX-ACCESS  read-write
    STATUS      current
    DESCRIPTION "volume name for file sharing"
    ::= { arrisRouterUsbShareFolderEntry 3 }

arrisRouterUsbShareFloderName OBJECT-TYPE
    SYNTAX      DisplayString (SIZE (0..255))
    MAX-ACCESS  read-write
    STATUS      current
    DESCRIPTION "volume name for file sharing"
    ::= { arrisRouterUsbShareFolderEntry 4 }

arrisRouterUsbShareName OBJECT-TYPE
    SYNTAX      DisplayString (SIZE (0..64))
    MAX-ACCESS  read-write
    STATUS      current
    DESCRIPTION "volume name for file sharing"
    ::= { arrisRouterUsbShareFolderEntry 5 }

arrisRouterUsbShareAdminAccess OBJECT-TYPE
    SYNTAX      TruthValue
    MAX-ACCESS  read-write
    STATUS      current
    DESCRIPTION "Enable or disable admin access"
    DEFVAL     { true }
    ::= { arrisRouterUsbShareFolderEntry 6 }

arrisRouterUsbShareEveryAccess OBJECT-TYPE
    SYNTAX      TruthValue
    MAX-ACCESS  read-write
    STATUS      current
    DESCRIPTION "Enable or disable everyone access"
    DEFVAL     { false }
    ::= { arrisRouterUsbShareFolderEntry 7 }

arrisRouterUsbShareSN OBJECT-TYPE
    SYNTAX      DisplayString (SIZE (0..64))
    MAX-ACCESS  read-only
    STATUS      current
    DESCRIPTION "Serial number of curreponding USB device"
    ::= { arrisRouterUsbShareFolderEntry 8 }

arrisRouterUsbDefaultRule OBJECT-TYPE
    SYNTAX      TruthValue
    MAX-ACCESS  read-only
    STATUS      current
    DESCRIPTION "The sharing rlue is default rule"
    ::= { arrisRouterUsbShareFolderEntry 9 }

arrisRouterUsbShareStatus OBJECT-TYPE
    SYNTAX      Unsigned32 (0..2)
    MAX-ACCESS  read-only
    STATUS      current
    DESCRIPTION "Check the status of sharing table
                  for default rule => 0:removed, 1:exist but not modified, 2: be modified
                  for usr add/modify => only vale 1: exist"
    ::= { arrisRouterUsbShareFolderEntry 10 }

-- media sharing
arrisRouterUsbEnableMediaSharing OBJECT-TYPE
    SYNTAX      TruthValue
    MAX-ACCESS  read-write
    STATUS      current
    DESCRIPTION  "Enable/disable media sharing"
    DEFVAL	{ false }
    ::= { arrisRouterUsbConfig 4 }

arrisRouterUsbMediaSharingName OBJECT-TYPE
    SYNTAX      DisplayString (SIZE (0..64))
    MAX-ACCESS  read-write
    STATUS      current
    DESCRIPTION "media sharing name"
    ::= { arrisRouterUsbConfig 5 }

arrisRouterStatsMgmt          OBJECT IDENTIFIER ::= { arrisRouterMibObjects 13 }

arrisRouterWiFiStatsObjects   OBJECT IDENTIFIER ::= { arrisRouterStatsMgmt 1 }

arrisRouterWiFiSSIDStatsTable OBJECT-TYPE
     SYNTAX       SEQUENCE OF ArrisRouterWiFiSSIDStatsEntry
     MAX-ACCESS   not-accessible
     STATUS       current
     DESCRIPTION  "Table contains information for a ArrisRouterWiFiSSIDStatsEntry"
     ::= { arrisRouterWiFiStatsObjects  1 }

arrisRouterWiFiSSIDStatsEntry OBJECT-TYPE
     SYNTAX       ArrisRouterWiFiSSIDStatsEntry
     MAX-ACCESS   not-accessible
     STATUS       current
     DESCRIPTION  "Table contains info for SSID stats"
     INDEX { ifIndex }
     ::= { arrisRouterWiFiSSIDStatsTable 1 }

ArrisRouterWiFiSSIDStatsEntry ::=
         SEQUENCE    {
                arrisRouterWiFiSSIDStatsTxOkBytes        Unsigned32,
                arrisRouterWiFiSSIDStatsRxOkBytes        Unsigned32,
                arrisRouterWiFiSSIDStatsTxOk             Unsigned32,
                arrisRouterWiFiSSIDStatsRxOk             Unsigned32
         }

arrisRouterWiFiSSIDStatsTxOkBytes OBJECT-TYPE
     SYNTAX       Unsigned32
     MAX-ACCESS   read-only
     STATUS       current
     DESCRIPTION  "Per SSID number of bytes in successfully transmitted. MSDU (data MPDU)."
     DEFVAL { 0 }
     ::= { arrisRouterWiFiSSIDStatsEntry 1 }

arrisRouterWiFiSSIDStatsRxOkBytes OBJECT-TYPE
     SYNTAX       Unsigned32
     MAX-ACCESS   read-only
     STATUS       current
     DESCRIPTION  "Per SSID number of bytes in Ethernet frames forwarded to stack by UMAC."
     DEFVAL { 0 }
     ::= { arrisRouterWiFiSSIDStatsEntry 2 }

arrisRouterWiFiSSIDStatsTxOk OBJECT-TYPE
     SYNTAX       Unsigned32
     MAX-ACCESS   read-only
     STATUS       current
     DESCRIPTION  "Per SSID number of successfully transmitted MSDU (data MPDU)."
     DEFVAL { 0 }
     ::= { arrisRouterWiFiSSIDStatsEntry 3 }

arrisRouterWiFiSSIDStatsRxOk OBJECT-TYPE
     SYNTAX       Unsigned32
     MAX-ACCESS   read-only
     STATUS       current
     DESCRIPTION  "Per SSID number of Ethernet frames forwarded to stack by UMAC."
     DEFVAL { 0 }
     ::= { arrisRouterWiFiSSIDStatsEntry 4 }

arrisRouterWiFiRadioStatsTable OBJECT-TYPE
     SYNTAX       SEQUENCE OF ArrisRouterWiFiRadioStatsEntry
     MAX-ACCESS   not-accessible
     STATUS       current
     DESCRIPTION  "Table contains information for a ArrisRouterWiFiRadioStatsEntry"
     ::= { arrisRouterWiFiStatsObjects  2 }

arrisRouterWiFiRadioStatsEntry OBJECT-TYPE
     SYNTAX       ArrisRouterWiFiRadioStatsEntry
     MAX-ACCESS   not-accessible
     STATUS       current
     DESCRIPTION  "Table contains information Radio Stats!"
     INDEX { ifIndex }
     ::= { arrisRouterWiFiRadioStatsTable 1 }

ArrisRouterWiFiRadioStatsEntry ::=
        SEQUENCE    {
               arrisRouterWiFiRadioStatsTxOk             Unsigned32,
               arrisRouterWiFiRadioStatsTxOkBytes        Unsigned32,
               arrisRouterWiFiRadioStatsTxFailed         Unsigned32,
               arrisRouterWiFiRadioStatsMgtTxOk          Unsigned32,
               arrisRouterWiFiRadioStatsMgtTxFailed      Unsigned32,
               arrisRouterWiFiRadioStatsTxbyrate         DisplayString,
               arrisRouterWiFiRadioStatsRxOk             Unsigned32,
               arrisRouterWiFiRadioStatsRxOkBytes        Unsigned32,
               arrisRouterWiFiRadioStatsMgtRxOk          Unsigned32,
               arrisRouterWiFiRadioStatsRxbyrate         DisplayString,
               arrisRouterWiFiRadioStatsTxDropped        Unsigned32,
               arrisRouterWiFiRadioStatsRxDropped        Unsigned32,
               arrisRouterWiFiRadioStatsTxOffer          Unsigned32,
               arrisRouterWiFiRadioStatsRxOffer          Unsigned32,
               arrisRouterWiFiRadioStatsTxErrorRate      Unsigned32,
               arrisRouterWiFiRadioStatsRxFailed         Unsigned32,
               arrisRouterWiFiRadioStatsTxOfferBytes     Unsigned32,
               arrisRouterWiFiRadioStatsRxOfferBytes     Unsigned32
       }

arrisRouterWiFiRadioStatsTxOk OBJECT-TYPE
     SYNTAX       Unsigned32
     MAX-ACCESS   read-only
     STATUS       current
     DESCRIPTION  "Number of successfully transmitted MSDU."
     DEFVAL { 0 }
     ::= { arrisRouterWiFiRadioStatsEntry 1 }

arrisRouterWiFiRadioStatsTxOkBytes OBJECT-TYPE
     SYNTAX       Unsigned32
     MAX-ACCESS   read-only
     STATUS       current
     DESCRIPTION  "Number of bytes in successfully transmitted MSDU (data MPDU)."
     DEFVAL { 0 }
     ::= { arrisRouterWiFiRadioStatsEntry 2 }

arrisRouterWiFiRadioStatsTxFailed OBJECT-TYPE
     SYNTAX       Unsigned32
     MAX-ACCESS   read-only
     STATUS       current
     DESCRIPTION  "Number of HW Tx errors and excessive retries for MSDU (data MPDU)."
     DEFVAL { 0 }
     ::= { arrisRouterWiFiRadioStatsEntry 3 }

arrisRouterWiFiRadioStatsMgtTxOk  OBJECT-TYPE
     SYNTAX       Unsigned32
     MAX-ACCESS   read-only
     STATUS       current
     DESCRIPTION  "Number of MMPDU successfully transmitted."
     DEFVAL { 0 }
     ::= { arrisRouterWiFiRadioStatsEntry 4 }

arrisRouterWiFiRadioStatsMgtTxFailed  OBJECT-TYPE
     SYNTAX       Unsigned32
     MAX-ACCESS   read-only
     STATUS       current
     DESCRIPTION  "Number of HW Tx errors and excessive retries for MMPDU."
     DEFVAL { 0 }
     ::= { arrisRouterWiFiRadioStatsEntry 5 }

arrisRouterWiFiRadioStatsTxbyrate  OBJECT-TYPE
     SYNTAX       DisplayString  (SIZE(1..255))
     MAX-ACCESS   read-only
     STATUS       current
     DESCRIPTION  "Number of Data MPDU transmitted for each MCS (modulation/coding scheme)."
     ::= { arrisRouterWiFiRadioStatsEntry 6 }

arrisRouterWiFiRadioStatsRxOk OBJECT-TYPE
     SYNTAX       Unsigned32
     MAX-ACCESS   read-only
     STATUS       current
     DESCRIPTION  "Number of Ethernet frames forwarded to stack by UMAC."
     DEFVAL { 0 }
     ::= { arrisRouterWiFiRadioStatsEntry 7 }

arrisRouterWiFiRadioStatsRxOkBytes OBJECT-TYPE
     SYNTAX       Unsigned32
     MAX-ACCESS   read-only
     STATUS       current
     DESCRIPTION  "Number of bytes in Ethernet frames forwarded to stack by UMAC."
     DEFVAL { 0 }
     ::= { arrisRouterWiFiRadioStatsEntry 8 }

arrisRouterWiFiRadioStatsMgtRxOk OBJECT-TYPE
     SYNTAX       Unsigned32
     MAX-ACCESS   read-only
     STATUS       current
     DESCRIPTION  "Number of MMPDU successfully received by the HW."
     DEFVAL { 0 }
     ::= { arrisRouterWiFiRadioStatsEntry 9 }

arrisRouterWiFiRadioStatsRxbyrate OBJECT-TYPE
     SYNTAX       DisplayString (SIZE(1..255))
     MAX-ACCESS   read-only
     STATUS       current
     DESCRIPTION  "Number of data MPDU received for each MCS (modulation/coding scheme)."
     ::= { arrisRouterWiFiRadioStatsEntry 10 }

arrisRouterWiFiRadioStatsTxDropped OBJECT-TYPE
     SYNTAX       Unsigned32
     MAX-ACCESS   read-only
     STATUS       current
     DESCRIPTION  "Number of Transmit packets that has been dropped."
     DEFVAL { 0 }
     ::= { arrisRouterWiFiRadioStatsEntry 11 }

arrisRouterWiFiRadioStatsRxDropped OBJECT-TYPE
     SYNTAX       Unsigned32
     MAX-ACCESS   read-only
     STATUS       current
     DESCRIPTION  "Number of Reception packets that has been dropped."
     DEFVAL { 0 }
     ::= { arrisRouterWiFiRadioStatsEntry 12 }

arrisRouterWiFiRadioStatsTxOffer OBJECT-TYPE
     SYNTAX       Unsigned32
     MAX-ACCESS   read-only
     STATUS       current
     DESCRIPTION  "Number of Ethernet frames at the entrance of the UMAC."
     DEFVAL { 0 }
     ::= { arrisRouterWiFiRadioStatsEntry 13 }

arrisRouterWiFiRadioStatsRxOffer OBJECT-TYPE
     SYNTAX       Unsigned32
     MAX-ACCESS   read-only
     STATUS       current
     DESCRIPTION  "Number of Data MPDU received from the radio."
     DEFVAL { 0 }
     ::= { arrisRouterWiFiRadioStatsEntry 14 }

arrisRouterWiFiRadioStatsTxErrorRate OBJECT-TYPE
     SYNTAX       Unsigned32
     MAX-ACCESS   read-only
     STATUS       current
     DESCRIPTION  "Transmitted packets error rate."
     DEFVAL { 0 }
     ::= { arrisRouterWiFiRadioStatsEntry 15 }

arrisRouterWiFiRadioStatsRxFailed OBJECT-TYPE
     SYNTAX       Unsigned32
     MAX-ACCESS   read-only
     STATUS       current
     DESCRIPTION  "Number of data MPDU missed by sequence number gap."
     DEFVAL { 0 }
     ::= { arrisRouterWiFiRadioStatsEntry 16 }

arrisRouterWiFiRadioStatsTxOfferBytes OBJECT-TYPE
     SYNTAX       Unsigned32
     MAX-ACCESS   read-only
     STATUS       current
     DESCRIPTION  "Number of bytes in Ethernet frames at the entrance of the UMAC."
     DEFVAL { 0 }
     ::= { arrisRouterWiFiRadioStatsEntry 17 }

arrisRouterWiFiRadioStatsRxOfferBytes OBJECT-TYPE
     SYNTAX       Unsigned32
     MAX-ACCESS   read-only
     STATUS       current
     DESCRIPTION  "Number of bytes in the data MPDU received from the radio."
     DEFVAL { 0 }
     ::= { arrisRouterWiFiRadioStatsEntry 18 }

arrisRouterTunnelStatsTable OBJECT-TYPE
     SYNTAX       SEQUENCE OF ArrisRouterTunnelStatsEntry
     MAX-ACCESS   not-accessible
     STATUS       current
     DESCRIPTION  "Table contains information for a ArrisRouterTunnelStatsEntry"
     ::= { arrisRouterStatsMgmt  2 }

arrisRouterTunnelStatsEntry OBJECT-TYPE
     SYNTAX       ArrisRouterTunnelStatsEntry
     MAX-ACCESS   not-accessible
     STATUS       current
     DESCRIPTION  "Table contains info for Tunnel stats"
     INDEX { ifIndex }
     ::= { arrisRouterTunnelStatsTable 1 }

ArrisRouterTunnelStatsEntry ::=
        SEQUENCE    {
               arrisRouterTunnelStatstunnelEngine        Unsigned32,
               arrisRouterTunnelStatstunnel              DisplayString,
               arrisRouterTunnelStatsuas                 Unsigned32,
               arrisRouterTunnelStatsrxPkts              Unsigned32,
               arrisRouterTunnelStatstxPkts              Unsigned32,
               arrisRouterTunnelStatsrxMBytes            DisplayString,
               arrisRouterTunnelStatstxMBytes            DisplayString,
               arrisRouterTunnelStatsdownEvents          Unsigned32
       }

arrisRouterTunnelStatstunnelEngine OBJECT-TYPE
     SYNTAX       Unsigned32
     MAX-ACCESS   read-only
     STATUS       current
     DESCRIPTION  "A default engine ID is generated during the process of the soft tunnel generation, RFC."
     DEFVAL { 0 }
     ::= { arrisRouterTunnelStatsEntry 1 }

arrisRouterTunnelStatstunnel OBJECT-TYPE
     SYNTAX       DisplayString (SIZE(1..32))
     MAX-ACCESS   read-only
     STATUS       current
     DESCRIPTION  "Indicates tunnel is operating on Primary or secondary."
     ::= { arrisRouterTunnelStatsEntry 2 }

arrisRouterTunnelStatsuas OBJECT-TYPE
     SYNTAX       Unsigned32
     MAX-ACCESS   read-only
     STATUS       current
     DESCRIPTION  "The time where the Soft-GRE tunnel is unavailable."
     DEFVAL { 0 }
     ::= { arrisRouterTunnelStatsEntry 3 }

arrisRouterTunnelStatsrxPkts OBJECT-TYPE
     SYNTAX       Unsigned32
     MAX-ACCESS   read-only
     STATUS       current
     DESCRIPTION  "Number of received packets in the Soft GRE tunnel."
     DEFVAL { 0 }
     ::= { arrisRouterTunnelStatsEntry 4 }

arrisRouterTunnelStatstxPkts OBJECT-TYPE
     SYNTAX       Unsigned32
     MAX-ACCESS   read-only
     STATUS       current
     DESCRIPTION  "Number of transmitted packets in the Soft GRE tunnel."
     DEFVAL { 0 }
     ::= { arrisRouterTunnelStatsEntry 5 }

arrisRouterTunnelStatsrxMBytes OBJECT-TYPE
     SYNTAX       DisplayString  (SIZE(1..32))
     MAX-ACCESS   read-only
     STATUS       current
     DESCRIPTION  "Number of received Mbytes in the Soft GRE tunnel."
     ::= { arrisRouterTunnelStatsEntry 6 }

arrisRouterTunnelStatstxMBytes OBJECT-TYPE
     SYNTAX       DisplayString  (SIZE(1..32))
     MAX-ACCESS   read-only
     STATUS       current
     DESCRIPTION  "Number of transmitted Mbytes in the Soft GRE tunnel."
     ::= { arrisRouterTunnelStatsEntry 7 }

arrisRouterTunnelStatsdownEvents OBJECT-TYPE
     SYNTAX       Unsigned32
     MAX-ACCESS   read-only
     STATUS       current
     DESCRIPTION  "Number of times the tunnel went down."
     DEFVAL { 0 }
     ::= { arrisRouterTunnelStatsEntry 8}

arrisRouterSamKnowsMgmt          OBJECT IDENTIFIER ::= { arrisRouterMibObjects 14 }

arrisRouterSamKnowsEnable OBJECT-TYPE
     SYNTAX      TruthValue
     MAX-ACCESS  read-write
     STATUS      current
     DESCRIPTION "Enable/Disable Samknows client test tool."
     DEFVAL { false }
     ::= { arrisRouterSamKnowsMgmt 1 }

END
