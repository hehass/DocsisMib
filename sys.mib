RFC1213-MIB DEFINITIONS ::= BEGIN

 IMPORTS
	mgmt, TimeTicks
		 FROM RFC1155-SMI
	OBJECT-TYPE
		  FROM RFC-1212;

 --  MIB-II (same prefix as MIB-I)

 mib-2      OBJECT IDENTIFIER ::= { mgmt 1 }

 -- textual conventions

 DisplayString ::=
	  OCTET STRING
 -- This data type is used to model textual information taken
 -- from the NVT ASCII character set.  By convention, objects
 -- with this syntax are declared as having
 --
 --      SIZE (0..255)

 -- groups in MIB-II

 system       OBJECT IDENTIFIER ::= { mib-2 1 }


 -- the System group

 -- Implementation of the System group is mandatory for all
 -- systems.  If an agent is not configured to have a value
 -- for any of these variables, a string of length 0 is
 -- returned.

 sysDescr OBJECT-TYPE
	  SYNTAX  DisplayString (SIZE (0..255))
	  ACCESS  read-only
	  STATUS  mandatory
	  DESCRIPTION
		 "A textual description of the entity.  This value
		 should include the full name and version
		 identification of the system's hardware type,
		 software operating-system, and networking
		 software.  It is mandatory that this only contain
		 printable ASCII characters."
	  ::= { system 1 }

 sysObjectID OBJECT-TYPE
	  SYNTAX  OBJECT IDENTIFIER
	  ACCESS  read-only
	  STATUS  mandatory
	  DESCRIPTION
		 "The vendor's authoritative identification of the
		 network management subsystem contained in the
		 entity.  This value is allocated within the SMI
		 enterprises subtree (1.3.6.1.4.1) and provides an
		 easy and unambiguous means for determining `what
		 kind of box' is being managed.  For example, if
		 vendor `Flintstones, Inc.' was assigned the
		 subtree 1.3.6.1.4.1.4242, it could assign the
		 identifier 1.3.6.1.4.1.4242.1.1 to its `Fred
		 Router'."
	  ::= { system 2 }

 sysUpTime OBJECT-TYPE
	  SYNTAX  TimeTicks
	  ACCESS  read-only
	  STATUS  mandatory
	  DESCRIPTION
		 "The time (in hundredths of a second) since the
		 network management portion of the system was last
		 re-initialized."
	  ::= { system 3 }

 sysContact OBJECT-TYPE
	  SYNTAX  DisplayString (SIZE (0..255))
	  ACCESS  read-only
	  STATUS  mandatory
	  DESCRIPTION
		 "The textual identification of the contact person
		 for this managed node, together with information
		 on how to contact this person."
	  ::= { system 4 }

 sysName OBJECT-TYPE
	  SYNTAX  DisplayString (SIZE (0..255))
	  ACCESS  read-only
	  STATUS  mandatory
	  DESCRIPTION
		 "An administratively-assigned name for this
		 managed node.  By convention, this is the node's
		 fully-qualified domain name."
	  ::= { system 5 }

 sysLocation OBJECT-TYPE
	  SYNTAX  DisplayString (SIZE (0..255))
	  ACCESS  read-only
	  STATUS  mandatory
	  DESCRIPTION
		 "The physical location of this node (e.g.,
		 `telephone closet, 3rd floor')."
	  ::= { system 6 }

 sysServices OBJECT-TYPE
	  SYNTAX  INTEGER (0..127)
	  ACCESS  read-only
	  STATUS  mandatory
	  DESCRIPTION
		 "A value which indicates the set of services that
		 this entity primarily offers.

		 The value is a sum.  This sum initially takes the
		 value zero, Then, for each layer, L, in the range
		 1 through 7, that this node performs transactions
		 for, 2 raised to (L - 1) is added to the sum.  For
		 example, a node which performs primarily routing
		 functions would have a value of 4 (2^(3-1)).  In
		 contrast, a node which is a host offering
		 application services would have a value of 72
		 (2^(4-1) + 2^(7-1)).  Note that in the context of
		 the Internet suite of protocols, values should be
		 calculated accordingly:

			layer  functionality
			 1  physical (e.g., repeaters)
			 2  datalink/subnetwork (e.g., bridges)
			 3  internet (e.g., IP gateways)
			 4  end-to-end  (e.g., IP hosts)
			 7  applications (e.g., mail relays)

		 For systems including OSI protocols, layers 5 and
		 6 may also be counted."
	  ::= { system 7 }

 END
