CL-PKTC-EUE-EVENT-MIB DEFINITIONS ::= BEGIN

IMPORTS
    
    OBJECT-TYPE,
    MODULE-IDENTITY    FROM SNMPv2-SMI     
    OBJECT-GROUP,
    MODULE-COMPLIANCE  FROM SNMPv2-CONF   
    SnmpAdminString
                       FROM SNMP-FRAMEWORK-MIB
    pktcEUEMibs        FROM CLAB-DEF-MIB;
    
          
pktcEUEEventMIB MODULE-IDENTITY
    LAST-UPDATED "200711060000Z"   
    ORGANIZATION "Cable Television Laboratories, Inc."
    CONTACT-INFO
            "Sumanth Channabasappa 
             Postal: Cable Television Laboratories, Inc
             858 Coal Creek Circle
             Louisville, CO 80027
             U.S.A.
             Phone: +1 303 661 9100
             Fax: +1 303 661 9199
             E-mail:mibs@cablelabs.com

             Acknowledgements:
             Thomas Clack, Broadcom - Primary author,
             and members of the PacketCable PACM Focus Team."

    DESCRIPTION
            "This MIB module provides the management objects for the 
            Management Event mechanism as specified by the PacketCable 
            E-UE Provisioning Framework."
    ::= { pktcEUEMibs 6 }

-- Administrative assignments   
pktcEUEEventNotifications     OBJECT IDENTIFIER ::= { pktcEUEEventMIB 0 } 
pktcEUEEventObjects           OBJECT IDENTIFIER ::= { pktcEUEEventMIB 1 }
pktcEUEEventConformance       OBJECT IDENTIFIER ::= { pktcEUEEventMIB 2 } 

pktcEUEMEMVersion OBJECT-TYPE
    SYNTAX      SnmpAdminString(SIZE(0..6))
    MAX-ACCESS  read-only
    STATUS      current
    DESCRIPTION
        " This MIB Object represents the Management Event Reporting Module 
          version. The eUE MUST set this MIB Object to value of '1.0'."
    ::= { pktcEUEEventObjects  1 }

-- Object Groups
--    The object groups used in this MIB module are imported from
--    the PKTC-EVENT-MIB (PKT-SP-EVEMIB1.5).

-- Conformance Statements
pktcEUEEventCompliances  OBJECT IDENTIFIER ::= { pktcEUEEventConformance 1 }
pktcEUEEventGroups       OBJECT IDENTIFIER ::= { pktcEUEEventConformance 2 }

-- Compliance Statements
pktcEUEEventCompliance MODULE-COMPLIANCE
    STATUS      current
    DESCRIPTION               
        "The compliance statement for CableLabs compliant eUE devices
        that implement the PacketCable E-UE Provisioning Framework.
        
        This compliance statement specifies, for PacketCable 
        E-UE Provisioning, the required objects from the PKTC-EVENT-MIB
        defined in the PacketCable 1.5 Specifications Management Event 
        MIB Specification, PKT-SP-EVEMIB1.5-I02-050812.
        
        Some objects from RFC4682 have been enhanced for applicability
        to eUEs. Similarly, inapplicable objects are clearly indicated."

    REFERENCE
        "PacketCable Embedded UE Provisioning Framework Specification"
    
    MODULE   PKTC-EVENT-MIB
        MANDATORY-GROUPS {
                 pktcEventGroup, 
                 pktcEventNotificationGroup
                 }

  MODULE   
        MANDATORY-GROUPS {
               pktcEUEMEMGroup
        }
    ::= { pktcEUEEventCompliances 1 }    
     
pktcEUEMEMGroup OBJECT-GROUP
      OBJECTS { 
          pktcEUEMEMVersion
      }
      STATUS  current
      DESCRIPTION
            "The eUE Operator Group."
      ::= { pktcEUEEventGroups 1} 

         
--  Notifications      
    
  --  pktcDevEvInform NOTIFICATION-TYPE          - Same as PKTC-EVENT-MIB
  --   OBJECTS {pktcDevEvLogIndex, pktcDevEvLogTime,
  --   pktcDevEvLogEnterprise,pktcDevEvLogId,
  --   pktcDevEvLogEndpointName,pktcDevEvLogCorrelationId,ifPhysAddress}
  
  -- pktcDevEvTrap NOTIFICATION-TYPE             - Same as PKTC-EVENT-MIB
  --  OBJECTS {pktcDevEvLogIndex, pktcDevEvLogTime,
  --  pktcDevEvLogEnterprise,pktcDevEvLogId,
  --  pktcDevEvLogEndpointName,pktcDevEvLogCorrelationId,ifPhysAddress}

 END
