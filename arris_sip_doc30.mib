ARRIS-SIP-DOC30-MIB DEFINITIONS ::= BEGIN

IMPORTS
 MODULE-IDENTITY, OBJECT-TYPE, Integer32, IpAddress
  FROM SNMPv2-SMI
 arrisSipMib
  FROM ARRIS-SIP-MIB
 OBJECT-GROUP
  FROM SNMPv2-CONF
 TruthValue, DisplayString, TEXTUAL-CONVENTION
  FROM SNMPv2-TC;

sipCfgDoc30 MODULE-IDENTITY
  LAST-UPDATED   "200908280000Z" -- August 28, 2009
  ORGANIZATION   "Arris Interactive"
  CONTACT-INFO
  "Caleb Atkins
   Postal: Arris Interactive
    3871 Lakefield Drive
    Suite 300
    Suwanee, GA 30024-1242
    U.S.A.
   Phone: +1 678 473 8693
   Email: caleb.atkins@arrisi.com"
  DESCRIPTION
    "SIP configuration settings that are specific to the ARRIS SIP products on DOCSIS 3.0.
     Most mibs in the ARRIS-SIP-MIB module are supported on both DOCSIS 2.0 and DOCSIS 3.0 platforms;
     however, mibs in the ARRIS-SIP-DOC30-MIB module are only supported in Arris TS7.1 loads and later."
  ::= { arrisSipMib 3 }


sipCfgDoc30FeatureSwitch OBJECT-TYPE
  SYNTAX BITS {
      removeMACfromUAHeader(0),
      unused1(1),
      unused2(2),
      unused3(3),
      unused4(4),
      unused5(5),
      unused6(6),
      unused7(7),
      unused8(8),
      unused9(9),
      unused10(10),
      unused11(11),
      unused12(12),
      unused13(13),
      unused14(14),
      unused15(15),
      unused16(16),
      unused17(17),
      unused18(18),
      unused19(19),
      unused20(20),
      unused21(21),
      unused22(22),
      unused23(23),
      unused24(24),
      unused25(25),
      unused26(26),
      unused27(27),
      unused28(28),
      unused29(29),
      unused30(30),
      unused31(31)
  }
  MAX-ACCESS read-write
  STATUS current
  DESCRIPTION
    "This MIB object is used to enable / disable SIP features that are specific to TS7.1 releases and later.

     /** BIT Descriptions **/
     0x80000000 : removeMACfromUAheader - Remove the SN/<MAC_addr> portion of the SIP User Agent header.
     0x40000000 : Reserved for Future.
     0x20000000 : Reserved for Future.
     0x10000000 : Reserved for Future.
     0x08000000 : Reserved for Future.
     0x04000000 : Reserved for Future.
     0x02000000 : Reserved for Future.
     0x01000000 : Reserved for Future.
     0x08000000 : Reserved for Future.
     0x04000000 : Reserved for Future.
     0x02000000 : Reserved for Future.
     0x01000000 : Reserved for Future.
     0x00800000 : Reserved for Future.
     0x00400000 : Reserved for Future.
     0x00200000 : Reserved for Future.
     0x00100000 : Reserved for Future.
     0x00080000 : Reserved for Future.
     0x00040000 : Reserved for Future.
     0x00020000 : Reserved for Future.
     0x00010000 : Reserved for Future.
     0x00008000 : Reserved for Future.
     0x00004000 : Reserved for Future.
     0x00002000 : Reserved for Future.
     0x00001000 : Reserved for Future.
     0x00000800 : Reserved for Future.
     0x00000400 : Reserved for Future.
     0x00000200 : Reserved for Future.
     0x00000100 : Reserved for Future.
     0x00000080 : Reserved for Future.
     0x00000040 : Reserved for Future.
     0x00000020 : Reserved for Future.
     0x00000010 : Reserved for Future.
     0x00000008 : Reserved for Future.
     0x00000004 : Reserved for Future.
     0x00000002 : Reserved for Future.
     0x00000001 : Reserved for Future."
  DEFVAL { '00000000'h }
 ::= { sipCfgDoc30 1 }


END
