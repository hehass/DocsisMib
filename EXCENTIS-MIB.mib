EXCENTIS-MIB DEFINITIONS ::= BEGIN

IMPORTS
   MODULE-IDENTITY,
   enterprises
       FROM SNMPv2-SMI;

excentis MODULE-IDENTITY
   LAST-UPDATED "200611150000Z" 
   ORGANIZATION "Excentis"
   CONTACT-INFO
       "Wim De Ketelaere 
        Gildestraat 8
        B-9000 Ghent
        Belgium
        Tel: +32 9 269 22 91
        Fax: +32 9 329 31 74
        Email: wim.deketelaere@excentis.com"
   DESCRIPTION
        "This MIB module supplies the basic management
        object categories for Excentis."
   ::= { enterprises 7432 }

END
