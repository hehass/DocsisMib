ECL-DEF-MIB DEFINITIONS ::= BEGIN

IMPORTS
    MODULE-IDENTITY,
    OBJECT-TYPE,
    enterprises
                    FROM SNMPv2-SMI;

euroCableLabs MODULE-IDENTITY
    LAST-UPDATED "200601051000Z" -- 05 January 2006
    ORGANIZATION "EuroCableLabs"
    CONTACT-INFO
           "Editor: Volker Leisse
            Postal: EuroCableLabs
                    Avenue des Arts 36
                    1040 Brussels
                    Belgium
            Phone:  +49 531 391-2478
            Fax:    +49 531 391-5192
            E-mail: mib@eurocablelabs.com"
    DESCRIPTION
            "This MIB module defines the organization of the namespace
            for the EuroCableLabs enterprise OID registry.

            Copyright 2005 EuroCableLabs
            All rights reserved."

    REVISION "200601051000Z" -- 05 January 2006
    DESCRIPTION
            "This revision was published as ECL-SP-MIB-DEF-D01."
    ::= { enterprises 24624 }


-- Sub-tree for Registrations
eclFunction             OBJECT IDENTIFIER ::= { euroCableLabs 1 }

-- Sub-tree for Project Definitions
eclProject              OBJECT IDENTIFIER ::= { euroCableLabs 2 }
eclProjDocsis           OBJECT IDENTIFIER ::= { eclProject 1 }
eclProjPacketCable      OBJECT IDENTIFIER ::= { eclProject 2 }
 
-- Sub-tree for Global Security Definitions
eclSecurity             OBJECT IDENTIFIER ::= { euroCableLabs 3 }

-- Sub tree for cross project common MIB definitions 
eclCommon               OBJECT IDENTIFIER ::= { euroCableLabs 4 }

--
-- EuroPacketCable Project Sub-tree Definitions
--
pktcEclMtaMib OBJECT IDENTIFIER
    -- PacketCable MIB module defining the basic management object for
    -- the Multimedia Terminal Adapter (MTA) devices compliant with
    -- PacketCable requirements.
    -- Reference
    -- CableLabs PacketCable MTA Device Provisioning Specification and
    -- draft-ietf-ipcdn-pktc-mtamib-06
    ::= { eclProjPacketCable 1 }
 
pktcEclSigMib OBJECT IDENTIFIER
    -- PacketCable MIB module defining the basic management object for
    -- the PacketCable MTA Signaling protocols. This version of the MIB
    -- includes common signaling and Network Call Signaling (NCS)
    -- related signaling objects.
    -- Reference
    -- CableLabs PacketCable MTA Device Provisioning Specification and
    -- draft-ietf-ipcdn-pktc-signaling-09
    ::= { eclProjPacketCable 2 }
 
pktcEclEventMib OBJECT IDENTIFIER
    -- PacketCable MIB module defining the basic management objects for
    -- event reporting.
    -- Reference
    -- CableLabs PacketCable Management Event Specification
    ::= { eclProjPacketCable 3 }
 
pktcEclSecurity OBJECT IDENTIFIER
    -- OID reserved for security and used to specify errors
    -- that can be returned for the Kerberos KDC - Provisioning
    -- Server interface, or the MTA-CMS Kerberized IPsec interface, or
    -- the MTA-Provisioning Server Kerberized SNMPv3 interface.
    -- Reference
    -- CableLabs PacketCable Security Specification
    ::= { eclProjPacketCable 4 }
 
pktcEclLawfulIntercept OBJECT IDENTIFIER
    -- OID reserved for management objects for the PacketCable Lawful
    -- Intercept specifications between the Delivery Function
    -- and Collection Function. This OID is used to define the ASN.1
    -- syntax of related messages.
    -- Reference
    -- 
    ::= { eclProjPacketCable 5 }

-- 
-- Sub-tree for EuroPacketCable MIB Enhancements
--
pktcEclEnhancements OBJECT IDENTIFIER ::= { eclProjPacketCable 6 }

-- The following MIB OBJECTS are being introduced for 
-- incorporation of new MIB objects (MIB enhancements).
-- This includes new MIB objects being introduced
-- as part of the PacketCable MIB Enhancement efforts
-- and as a place holder for future revisions.
-- This sub-division would facilitate easier incorporation
-- of proposed IETF Drafts/RFCs by keeping enhancements
-- independent of RFC/Draft changes.
-- For new MIB tables that use previously used indices, it is 
-- recommended that the AUGMENT CLAUSE be used to aid SNMP Operations,
-- as deemed necessary.

pktcEclEnMtaMib OBJECT IDENTIFIER
    -- PacketCable MIB module enhancements to the basic management 
    -- objects defined by the MIB group pktcMtaMib for the Multimedia 
    -- Terminal Adapter (MTA) devices compliant with PacketCable 
    -- requirements.
    -- Reference:
    -- CableLabs PacketCable MTA Device Provisioning Specification.
    ::= { pktcEclEnhancements 1 }
 
pktcEclEnSigMib OBJECT IDENTIFIER
    -- PacketCable MIB module enhancements to the basic management 
    -- objects defined by the MIB group pktcSigMib for the 
    -- PacketCable MTA Signaling protocols. 
    -- Reference:
    -- CableLabs PacketCable MTA Device Provisioning Specification.
    ::= { pktcEclEnhancements 2 }
 
pktcEclEnEventMib OBJECT IDENTIFIER
    -- PacketCable MIB module enhancements to the basic management 
    -- objects defined by the MIB group pktcEventMib for event reporting.
    -- Reference:
    -- CableLabs PacketCable Management Event Specification.
    ::= { pktcEclEnhancements 3 }
 
pktcEclEnSecurityMib OBJECT IDENTIFIER
    -- PacketCable MIB module enhancements to the basic management
    -- objects defined by the reserved MIB group pktcSecurity.
    -- Reference:
    -- CableLabs PacketCable Security Specification.
    ::= { pktcEclEnhancements 4 }

END
